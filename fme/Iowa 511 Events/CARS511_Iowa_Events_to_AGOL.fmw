FME workspace CARS511_Iowa_Events_to_AGOL.fmw
Title: CARS511_Iowa_Events_to_AGOL
Description: This workflow parses the Castle Rock CARS 511 Events XML Feed for Iowa. It can be used to pull any CARS 511 XML feed (more information about other states is available on the 
        Castle Rock website 
    ). You can request CARS 511 XML datafeed credentials 
        here 
    .
This production workflow is used to write the following AGOL services:
IowaDOT_SODA Feature Service: http://services.arcgis.com/8lRhdTsQyJpO52F1/arcgis/rest/services/CARS511_Iowa/FeatureServer/0
IowaDOT_SODA Feature Collection: http://iowadot.maps.arcgis.com/sharing/rest/content/items/87b359a4ec4c489c801c8ca965f11f31/data
Requirements: XML Feed Requirements:
xfMap File: xfmap_CARS.xml
Iowa Route Directionality Listing CSV: Iowa Route Directionality Listing - REVISED 2015.csv
If writing to AGOL feature collections, the following files are needed:
    Feature Collection Update Requirements:
overwrite_CARS511Events.cfg: RESOURCES>ENGINE>PLUGINS>PYTHON via FME Server Web UI
overwrite_CARS511Events.py: RESOURCES>ENGINE>PLUGINS>PYTHON via FME Server Web UI
History: 5/8/2017,DR,Redacted internal paths and credentials for public version
Startup Python:
      #-------------------------------------------------------------------------------
      # Name:        Disables/ReEnables Editing for Service
      # Purpose:
      #
      # Author:      Kelly Gerrow/Hunter Praska/Mark McCart
      #Contact:      kgerrow@esri.com
      #
      # Created:     11/18/2015
      #-------------------------------------------------------------------------------
      """
      def getToken(adminUser, pw):
              data = {'username': adminUser,
                  'password': pw,
                  'referer' : 'https://www.arcgis.com',
                  'f': 'json'}
              url  = 'https://arcgis.com/sharing/rest/generateToken'
              jres = requests.post(url, data=data, verify=False).json()
              return jres['token'],jres['ssl']

      #generates account information
      def GetAccount(pref, tokenfun):
          URL= pref+'www.arcgis.com/sharing/rest/portals/self?f=json&token=' + tokenfun
          response = requests.get(URL, verify=False)
          jres = json.loads(response.text)
          return jres['urlKey']


      import requests, json

      #Enter Username and Password
      user= "[USERNAME]" #raw_input('What is the ArcGIS Online Username?')
      pw = "[PASSWORD]" #raw_input('What is the ArcGIS Online Password?')

      #get account information
      token= getToken(user, pw)
      if token[1] == False:
                 pref='http://'
      else:
                 pref='https://'
      #Create Portal URL
      t=GetAccount(pref,token[0])
      portalUrl=pref+t

      restURL511='http://services.arcgis.com/[AGOL ORGANIZATION ID]/ArcGIS/rest/admin/services/[SERVICE NAME]/FeatureServer/updateDefinition' #modify URL
      defCapabilities= '{"hasStaticData":false,"capabilities":"Query,Editing,Create,Update,Delete,Extract"}' #editing enabled
      #defCapabilities= '{"capabilities":"Query,Extract"}' #editing disabled
      data = {'updateDefinition': defCapabilities,
                  'token':token[0],
                  'f': 'json'}

      #Send Request
      res =requests.post(restURL511, data = data, verify=False).json()

      print res
      if res['success']==True:
          print 'Service successfully Added'
      else:
          print 'Service NOT ADDED'
      """
Shutdown Python:
      #-------------------------------------------------------------------------------
      # Name:        Disables/ReEnables Editing for Service & Writes Feature Collections to AGOL
      # Purpose:
      #
      # Authors:     Kelly Gerrow (Esri); Mark McCart (HNTB); Hunter Praska (Iowa DOT); Eric Rodenberg (Esri)
      # Contact:     kgerrow@esri.com; mmccart@hntb.com; hunter.praska@iowa.dot.gov; erodenberg@esri.com
      #
      # Created:     11/18/2015
      # Modified:    8/10/2016 - To include Feature Collection Creation on AGOL (Mark and Eric)
      #-------------------------------------------------------------------------------
      """
      def getToken(adminUser, pw):
              data = {'username': adminUser,
                  'password': pw,
                  'referer' : 'https://www.arcgis.com',
                  'f': 'json'}
              url  = 'https://arcgis.com/sharing/rest/generateToken'
              jres = requests.post(url, data=data, verify=False).json()
              return jres['token'],jres['ssl']

      #generates account information
      def GetAccount(pref, tokenfun):
          URL= pref+'www.arcgis.com/sharing/rest/portals/self?f=json&token=' + tokenfun
          response = requests.get(URL, verify=False)
          jres = json.loads(response.text)
          return jres['urlKey']


      import requests, json
      # Next 3 lines of code are required to copy/create Feature Collections on AGOL
      import sys
      from overwrite_CARS511Events import run #Rename 'overwrite_CARS511Events' to name of .py file you want to run. Store it here: C:\apps\FME\2016\python\python27\ for FME Desktop. For FME Server: Load to RESOURCES>ENGINE>PLUGINS>PYTHON via Web UI

      #Enter Username and Password
      user= "[USERNAME]" #raw_input('What is the ArcGIS Online Username?')
      pw = "[PASSWORD]" #raw_input('What is the ArcGIS Online Password?')

      #get account information
      token= getToken(user, pw)
      if token[1] == False:
                 pref='http://'
      else:
                 pref='https://'
      #Create Portal URL
      t=GetAccount(pref,token[0])
      portalUrl=pref+t


      restURL511='http://services.arcgis.com/[AGOL ORGANIZATION ID]/ArcGIS/rest/admin/services/[SERVICE NAME]/FeatureServer/updateDefinition' #modify URL
      defCapabilities= '{"capabilities":"Query,Extract"}' #editing disabled
      data = {'updateDefinition': defCapabilities,
                  'token':token[0],
                  'f': 'json'}

      #Send Request
      res =requests.post(restURL511, data = data, verify=False).json()
      print res
      if res['success']==True:
          print 'Service successfully Added'
      else:
          print 'Service NOT ADDED'

      # Run the Feature Collection creation script provided by Esri and modified for each FC
      config_file = r"C:\Apps\FME\python\python27\overwrite_CARS511Events.cfg" #For FME Desktop Only. Must copy .cfg and .py file here
      #config_file = r"C:\ProgramData\Safe Software\FME Server\resources\engine\Plugins\python\overwrite_CARS511Events.cfg" #For FME Server Only. Must load to FME Server Resources
      run(config_file)
      """

Parameters:
- SourceDataset_XML = http://ia.carsprogram.org/hub/data/feu-g.xml   # Source XML File(s)
- AUTH_USERNAME =   # Username
- AUTH_PASSWORD =   # Password
- XFMAP_XML = $(FME_MF_DIR)xfmap_CARS.xml   # xfMap File
- RouteCSV = $(FME_MF_DIR)Iowa Route Directionality Listing - REVISED 2015.csv   # CSV with Route and LinkDirection
- DestDataset_GEODATABASE_FILE = $(FME_MF_DIR)IA_CARS511_Events.gdb   # Destination Esri File Geodatabase
- SourceDataset_XML_6 = $(FME_MF_DIR)sampledata_iowa.xml   # Source XML File(s)

Readers:
- XML_1: XML from $(SourceDataset_XML)
- CSV_1: CSV from $(RouteCSV)
- XML_4: XML from $(SourceDataset_XML_6)

Writers:
- GEODATABASE_FILE_1: GEODATABASE_FILE to $(DestDataset_GEODATABASE_FILE) in SPHERICAL_MERCATOR

Note: PRE-REQUIREMENTS: / 1) I have provided a sample file available in \example data\ia_feu-g.xml. If yo uwould like access to the CARS 511 XML feed for your area (if available), click here for more information. / 2) The startup and shutdown python scripts needed to enable/disable editing, along with making high available feature collections are found in Workspace Parameters -> Advanced -> Startup Python Script and Shutdown Python Script. These are commented out, so you can run this workspace without them for testing/demonstration purposes. You will also need to move the overwrite_ files to your FME python folder.

Bookmark: Load XML & Set ORGID
  Loads Castle Rock's XML Feed for Iowa CARS 511 using xfMap File reader. Also filters out road condition segments and assigns a value to the ORGID field.
Note: Actual XML Feed Location
Feature (reader XML_1) [off]
    attributes: AltRoute xml_char(20), CrossRoad1 xml_char(25), CrossRoad2 xml_char(14), Descriptions xml_char(521), EndTimeDate xml_decimal(9,0), EndTimeTime xml_decimal(7,0), EndTimeUTCoffset xml_decimal(6,0), ID xml_char(14), Instructions xml_char(12), Latitude1 xml_decimal(9,0), Latitude2 xml_decimal(9,0), LinearReference1 xml_decimal(22,18), LinearReference2 xml_decimal(22,18), LinkDirection xml_char(19), Longitude1 xml_decimal(10,0), Longitude2 xml_decimal(10,0), MessageExpiryDate xml_decimal(9,0), MessageExpiryTime xml_decimal(7,0), MessageIssueDate xml_decimal(9,0), MessageIssueTime xml_decimal(7,0), MessageIssueUTCoffset xml_decimal(6,0), MessageNumber xml_decimal(6,0), OrganizationID xml_char(9), Ownership xml_char(11), Priority xml_decimal(3,0), Recommendations xml_char(16), RestrictionHeight xml_decimal(4,0), RestrictionLength xml_decimal(5,0), RestrictionWeightAxle xml_decimal(5,0), RestrictionWeightVehicle xml_decimal(6,0),
      RestrictionWidth xml_decimal(4,0), RouteDesignator xml_char(19), SpeedLimit xml_decimal(3,0), StartTimeDate xml_decimal(9,0), StartTimeTime xml_decimal(7,0), StartTimeUTCoffset xml_decimal(6,0), Status xml_char(8), Suggestions xml_char(11), Update xml_decimal(3,0), UpdateTimeDate xml_decimal(9,0), UpdateTimeTime xml_decimal(7,0), UpdateTimeUTCoffset xml_decimal(6,0), Warnings xml_char(45), ca_closure xml_char(8), ca_delay xml_char(6), ca_devicestat xml_char(7), ca_disaster xml_char(9), ca_disturbance xml_char(12), ca_incident xml_char(9), ca_mobsit xml_char(7), ca_obstruction xml_char(12), ca_parkinginfo xml_char(8), ca_pavementcond xml_char(19), ca_restriction xml_char(12), ca_roadwork xml_char(30), ca_specialevent xml_char(12), ca_sportsevent xml_char(7), ca_systeminfo xml_char(7), ca_traffic xml_char(18), ca_unusualdriving xml_char(8),
      ca_weather_cond xml_char(8), ca_winter_index xml_char(13), ca_winter_restriction xml_char(19), ca_wx_airquality xml_char(4), ca_wx_precip xml_char(7), ca_wx_temp xml_char(5), ca_wx_wind xml_char(5), hd_closure xml_char(30), hd_delay xml_char(9), hd_devicestat xml_char(14), hd_disaster xml_char(12), hd_disturbance xml_char(15), hd_incident xml_char(12), hd_mobsit xml_char(32), hd_obstruction xml_char(15), hd_parkinginfo xml_char(15), hd_pavementcond xml_char(16), hd_restriction xml_char(19), hd_roadwork xml_char(43), hd_specialevent xml_char(16), hd_sportsevent xml_char(15), hd_systeminfo xml_char(14), hd_traffic xml_char(11), hd_unusualdriving xml_char(18), hd_weather_cond xml_char(16), hd_winter_index xml_char(16), hd_winter_restriction xml_char(22), hd_wx_airquality xml_char(17), hd_wx_precip xml_char(13), hd_wx_temp xml_char(11),
      hd_wx_wind xml_char(11), ph_closure xml_char(8), ph_delay xml_char(6), ph_devicestat xml_char(7), ph_disaster xml_char(9), ph_disturbance xml_char(12), ph_incident xml_char(9), ph_mobsit xml_char(7), ph_obstruction xml_char(12), ph_parkinginfo xml_char(8), ph_pavementcond xml_char(19), ph_restriction xml_char(12), ph_roadwork xml_char(9), ph_specialevent xml_char(8), ph_sportsevent xml_char(7), ph_systeminfo xml_char(7), ph_traffic xml_char(18), ph_unusualdriving xml_char(8), ph_weather_cond xml_char(8), ph_winter_index xml_char(13), ph_winter_restriction xml_char(19), ph_wx_airquality xml_char(4), ph_wx_precip xml_char(7), ph_wx_temp xml_char(5), ph_wx_wind xml_char(5)
    -> Segment_Dropper
Note: Sample Data Feed
Feature (reader XML_4)
    attributes: AltRoute xml_char(20), CrossRoad1 xml_char(25), Descriptions xml_char(284), EndTimeDate xml_decimal(9,0), EndTimeTime xml_decimal(7,0), EndTimeUTCoffset xml_decimal(6,0), ID xml_char(14), Latitude1 xml_decimal(9,0), Latitude2 xml_decimal(9,0), LinearReference1 xml_decimal(22,18), LinearReference2 xml_decimal(21,17), LinkDirection xml_char(19), Longitude1 xml_decimal(10,0), Longitude2 xml_decimal(10,0), MessageExpiryDate xml_decimal(9,0), MessageExpiryTime xml_decimal(7,0), MessageIssueDate xml_decimal(9,0), MessageIssueTime xml_decimal(7,0), MessageIssueUTCoffset xml_decimal(6,0), MessageNumber xml_decimal(7,0), OrganizationID xml_char(9), Ownership xml_char(11), Priority xml_decimal(3,0), RestrictionHeight xml_decimal(4,0), RestrictionWeightAxle xml_decimal(6,0), RestrictionWeightVehicle xml_decimal(6,0), RestrictionWidth xml_decimal(4,0), RouteDesignator xml_char(19), StartTimeDate xml_decimal(9,0), StartTimeTime xml_decimal(7,0),
      StartTimeUTCoffset xml_decimal(6,0), Status xml_char(8), Update xml_decimal(4,0), UpdateTimeDate xml_decimal(9,0), UpdateTimeTime xml_decimal(7,0), UpdateTimeUTCoffset xml_decimal(6,0), Warnings xml_char(45), ca_roadwork xml_char(29), hd_closure xml_char(26), hd_restriction xml_char(19), hd_roadwork xml_char(43), ph_closure xml_char(26), ph_mobsit xml_char(32), ph_pavementcond xml_char(12), ph_restriction xml_char(36), ph_roadwork xml_char(43)
    -> Segment_Dropper
Segment_Dropper: AttributeFilter
    ATTR_NAME = OrganizationID
    ATTR_VALUES = <EMPTY>,<MISSING>,<NULL>,<UNFILTERED>,IASEG
    <UNFILTERED> -> IA_ORGID_Field
IA_ORGID_Field: AttributeCreator
    ATTR_TABLE = SET_TO ORGID = Iowa
    -> Geometry_Latitude_Filter_2

Bookmark: Geometry Tester & Creation
  Filters bad Lat/Long. Creates Point geometry based on Lat/Long. Reprojects from LL84 to Spherical Mercator.
Geometry_Latitude_Filter_2: AttributeFilter
    ATTR_NAME = Latitude1
    ATTR_VALUES = <EMPTY>,<MISSING>,<NULL>,<UNFILTERED>
    <UNFILTERED> -> Geometry_Longitude_Filter
Geometry_Longitude_Filter: AttributeFilter
    ATTR_NAME = Longitude1
    ATTR_VALUES = <EMPTY>,<MISSING>,<NULL>,<UNFILTERED>
    <UNFILTERED> -> GeometryFormatter
GeometryFormatter: StringFormatter
    FORMAT = .6f
    SRC_ATTRS = Latitude2,Longitude1,Latitude1,Longitude2
    -> Latitude_Divider
Latitude_Divider: ExpressionEvaluator
    VAL_ATTR = Latitude
    ACTION = Create New Attribute
    EXPRESSION = @Value(Latitude1)/1000000
    -> Longitude_Divider
Longitude_Divider: ExpressionEvaluator
    VAL_ATTR = Longitude
    ACTION = Create New Attribute
    EXPRESSION = @Value(Longitude1)/1000000
    -> VertexCreator
VertexCreator
    XVAL = @Value(Longitude)
    MODE_NAME = Add Point
    YVAL = @Value(Latitude)
    -> Reprojector
Reprojector
    DEST = SPHERICAL_MERCATOR
    RASTER_CELL_SIZE = Preserve Cells
    INTERPOLATION_TYPE_NAME = Nearest Neighbor
    SOURCE = LL-WGS84
    REPROJECTED -> TimeStamper

Bookmark: Date Validator
  1) Gets current YMD, 2) Calculate expired messages 3) Expired filter - Only pull current messages
TimeStamper
    FMT = FME Date (^Y^m^d)
    TIME_ATTR = GIS_UPDATED
    -> Expired_Date_Difference
Expired_Date_Difference: DateDifferenceCalculator
    Unit = 86400
    EndDate = @Value(EndTimeDate)
    FMT = %Y%m%d
    StartDate = @Value(GIS_UPDATED)
    Output_Name = Time_Difference
    -> Expired_Checker
Expired_Checker: AttributeRangeFilter
    LUT = -1000000000000,-.1,-1000000000000 .. -.1
    IN_ATTR = Time_Difference
    <UNFILTERED> -> Start_Date_Difference

Bookmark: Calculate Start Date Difference
Start_Date_Difference: DateDifferenceCalculator
    Unit = 86400
    EndDate = @Value(StartTimeDate)
    FMT = %Y%m%d
    StartDate = @Value(GIS_UPDATED)
    Output_Name = Time_Difference
    -> Future_Event_Checker

Bookmark: Filter Future Messages
Future_Event_Checker: AttributeRangeFilter
    LUT = -100000,0,-100000 .. 0,0,100000,0 .. 100000
    IN_ATTR = Time_Difference
    -100000 .. 0 -> Priority_Event_Filter
    0 .. 100000 -> Future_Event_Filter
    <UNFILTERED> -> Priority_Event_Filter
Future_Event_Filter: AttributeFilter
    ATTR_NAME = StartTimeDate
    ATTR_VALUES = <EMPTY>,<MISSING>,<NULL>,<UNFILTERED>
    <EMPTY> -> Priority_Event_Filter
    <MISSING> -> Priority_Event_Filter
    <NULL> -> Priority_Event_Filter
    <UNFILTERED> -> FutureAttribute

Bookmark: Priority=1
Priority_Event_Filter: AttributeRangeFilter
    LUT = 1,1,priority,2,100,other
    IN_ATTR = Priority
    priority -> Priority1_Reopened_2
    other -> Headline_Closure
Priority1_Reopened_2: StringSearcher
    CASE = no
    MATCHED_RESULT_ATTR = _matched_characters
    STRING_TO_SEARCH = @Value(hd_closure)
    MATCHED_PARTS_ATTR = _matched_parts
    REGEXP = Reopened to traffic
    MATCHED -> PriInfoAttribute
    NOT_MATCHED -> Priority1_Closure_Attribute_Filter
Priority1_Closure_Attribute_Filter: AttributeFilter
    ATTR_NAME = hd_closure
    ATTR_VALUES = <EMPTY>,<MISSING>,<NULL>,<UNFILTERED>
    <EMPTY> -> Priority1_Reopened
    <MISSING> -> Priority1_Reopened
    <NULL> -> Priority1_Reopened
    <UNFILTERED> -> PriClosureAttribute
Priority1_Reopened: StringSearcher
    CASE = no
    MATCHED_RESULT_ATTR = _matched_characters
    STRING_TO_SEARCH = @Value(ph_closure)
    MATCHED_PARTS_ATTR = _matched_parts
    REGEXP = Reopened to traffic
    MATCHED -> PriInfoAttribute
    NOT_MATCHED -> Pri1WarningAttribute

Bookmark: Check for Closure Type
Headline_Closure: AttributeFilter
    ATTR_NAME = hd_closure
    ATTR_VALUES = <EMPTY>,<MISSING>,<NULL>,<UNFILTERED>,alternating lane closures,bridge is closed,entrance ramp closed,exit ramp closed,intermittent lane closure,intersecting road closed,left lane closed,reduced to one lane,reduced to two lanes,right lane closed,right shoulder closed,shoulder closed,closed,blocked,road closure,left shoulder closed,center lane closed,closed intermittently,rest area closed,slow moving maintenance vehicle,single line traffic: alternating directions,flooding,reopened to traffic,detour in operation
    <EMPTY> -> HeadlineRoadwork
    <MISSING> -> HeadlineRoadwork
    <NULL> -> HeadlineRoadwork
    <UNFILTERED> -> lane_searcher
    alternating lane closures -> LaneAttribute
    bridge is closed -> ClosedAttribute
    entrance ramp closed -> WarningAttribute
    exit ramp closed -> WarningAttribute
    intermittent lane closure -> WarningAttribute
    intersecting road closed -> LaneAttribute
    left lane closed -> LaneAttribute
    reduced to one lane -> LaneAttribute
    reduced to two lanes -> LaneAttribute
    right lane closed -> LaneAttribute
    right shoulder closed -> WarningAttribute
    shoulder closed -> WarningAttribute
    closed -> ClosedAttribute
    blocked -> ClosedAttribute
    road closure -> ClosedAttribute
    left shoulder closed -> WarningAttribute
    center lane closed -> LaneAttribute
    closed intermittently -> WarningAttribute
    rest area closed -> InfoAttribute
    slow moving maintenance vehicle -> RoadworkAttribute
    single line traffic: alternating directions -> RoadworkAttribute
    flooding -> PriClosureAttribute
    reopened to traffic -> InfoAttribute
    detour in operation -> ClosedAttribute

Bookmark: Check for Roadwork
HeadlineRoadwork: StringSearcher
    CASE = no
    MATCHED_RESULT_ATTR = _matched_characters
    STRING_TO_SEARCH = @Value(hd_roadwork)
    MATCHED_PARTS_ATTR = _matched_parts
    REGEXP = " "
    MATCHED -> RoadworkAttribute
    NOT_MATCHED -> CauseRoadwork
CauseRoadwork: StringSearcher
    CASE = no
    MATCHED_RESULT_ATTR = _matched_characters
    STRING_TO_SEARCH = @Value(ca_roadwork)
    MATCHED_PARTS_ATTR = _matched_parts
    REGEXP = " "
    NOT_MATCHED -> hdRestriction

Bookmark: Check for Restrictions
hdRestriction: StringSearcher
    CASE = no
    MATCHED_RESULT_ATTR = _matched_characters
    STRING_TO_SEARCH = @Value(hd_restriction)
    MATCHED_PARTS_ATTR = _matched_parts
    REGEXP = " "
    MATCHED -> RestrictionAttribute
    NOT_MATCHED -> PhRestriction
PhRestriction: StringSearcher
    CASE = no
    MATCHED_RESULT_ATTR = _matched_characters
    STRING_TO_SEARCH = @Value(ph_restriction)
    MATCHED_PARTS_ATTR = _matched_parts
    REGEXP = " "
    MATCHED -> RestrictionAttribute
    NOT_MATCHED -> Delays

Bookmark: Check for Delays
Delays: StringSearcher
    CASE = no
    MATCHED_RESULT_ATTR = _matched_characters
    STRING_TO_SEARCH = @Value(ph_delay)
    MATCHED_PARTS_ATTR = _matched_parts
    REGEXP = delays
    MATCHED -> WarningAttribute
    NOT_MATCHED -> Delays_2
Delays_2: StringSearcher
    CASE = no
    MATCHED_RESULT_ATTR = _matched_characters
    STRING_TO_SEARCH = hd_delay
    MATCHED_PARTS_ATTR = _matched_parts
    REGEXP = delays
    MATCHED -> WarningAttribute
    NOT_MATCHED -> MobileSituation
lane_searcher: StringSearcher
    CASE = no
    MATCHED_RESULT_ATTR = _matched_characters
    STRING_TO_SEARCH = @Value(hd_closure)
    MATCHED_PARTS_ATTR = _matched_parts
    REGEXP = lane
    MATCHED -> LaneAttribute
    NOT_MATCHED -> ClosedAttribute

Bookmark: Check for Mobile Situation
MobileSituation: StringSearcher
    CASE = no
    MATCHED_RESULT_ATTR = _matched_characters
    STRING_TO_SEARCH = @Value(hd_mobsit)
    MATCHED_PARTS_ATTR = _matched_parts
    REGEXP = " "
    MATCHED -> WarningAttribute
    NOT_MATCHED -> JunkFilter
JunkFilter: TestFilter
    TEST_LIST:
      BOOL_OP,OR,COMPOSITE_TEST,<Unused>,TEST_CLAUSE,"TEST @Value(hd_restriction) CONTAINS roundabout
      TEST @Value(ph_restriction) CONTAINS roundabout",Roundabout,BOOL_OP,OR,COMPOSITE_TEST,<Unused>,TEST_CLAUSE,"TEST @Value(hd_incident) CONTAINS crash
      TEST @Value(hd_incident) CONTAINS stalled vehicle
      TEST @Value(hd_incident) CONTAINS traffic incident",Accidents,BOOL_OP,OR,COMPOSITE_TEST,<Unused>,TEST_CLAUSE,"TEST hd_pavementcond ATTRIBUTE_VALUE_NULL """"
      TEST hd_pavementcond ATTRIBUTE_IS_EMPTY """"
      TEST hd_pavementcond ATTRIBUTE_IS_MISSING """"",conditions
    DEFAULT_VALUE = <UNFILTERED>
    Accidents -> WarningAttribute
    <UNFILTERED> -> InfoAttribute

Bookmark: STYLE Attribute Creator
WarningAttribute: AttributeCreator
    ATTR_TABLE = SET_TO STYLE = warning
    -> AudioRemover
InfoAttribute: AttributeCreator
    ATTR_TABLE = SET_TO STYLE = info
    -> AudioRemover
RestrictionAttribute: AttributeCreator
    ATTR_TABLE = SET_TO STYLE = restriction
    -> AudioRemover
RoadworkAttribute: AttributeCreator
    ATTR_TABLE = SET_TO STYLE = roadwork
    -> AudioRemover
ClosedAttribute: AttributeCreator
    ATTR_TABLE = SET_TO STYLE = closure
    -> AudioRemover
LaneAttribute: AttributeCreator
    ATTR_TABLE = SET_TO STYLE = lane_closure
    -> AudioRemover
PriClosureAttribute: AttributeCreator
    ATTR_TABLE = SET_TO STYLE = priority_closure
    -> AudioRemover
PriInfoAttribute: AttributeCreator
    ATTR_TABLE = SET_TO STYLE = priority_info
    -> AudioRemover
Pri1WarningAttribute: AttributeCreator
    ATTR_TABLE = SET_TO STYLE = priority_warning
    -> Flooding_Formatter
Flooding_Formatter: AttributeCreator
    ATTR_TABLE:
      SET_TO hd_closure = FME_CONDITIONAL:DEFAULT_VALUE'_FME_NO_OP_'BOOL_OP;OR;COMPOSITE_TEST;<Unused>;TEST @Value(ca_obstruction) = flooding'flooding'FME_NUM_CONDITIONS2___
      SET_TO ph_closure = FME_CONDITIONAL:DEFAULT_VALUE'_FME_NO_OP_'BOOL_OP;OR;COMPOSITE_TEST;<Unused>;TEST @Value(ca_obstruction) = flooding'Closed'FME_NUM_CONDITIONS2___
      SET_TO STYLE = FME_CONDITIONAL:DEFAULT_VALUE'_FME_NO_OP_'BOOL_OP;OR;COMPOSITE_TEST;<Unused>;TEST @Value(ca_obstruction) = flooding'priority_closure'FME_NUM_CONDITIONS2___
    -> AudioRemover
FutureAttribute: AttributeCreator
    ATTR_TABLE = SET_TO STYLE = future_event
    -> AudioRemover

Bookmark: Description Formatting
AudioRemover: StringReplacer
    FIND_TEXT = "Audio Text: "
    CASE = NO
    NO_MATCH = _FME_NO_OP_
    SRC_ATTRS = Descriptions
    REGEXP = NO
    -> QuoteReplacer
QuoteReplacer: StringReplacer
    FIND_TEXT = ”
    CASE = NO
    REPLACE_TEXT = "
    NO_MATCH = _FME_NO_OP_
    SRC_ATTRS = RestrictionLength,RestrictionWidth,RestrictionHeight
    REGEXP = YES
    -> ApostropheReplacer
ApostropheReplacer: StringReplacer
    FIND_TEXT = ’
    CASE = NO
    REPLACE_TEXT = '
    NO_MATCH = _FME_NO_OP_
    SRC_ATTRS = RestrictionLength,RestrictionWidth,RestrictionHeight
    REGEXP = YES
    -> UpdatedAttribute
UpdatedAttribute: AttributeCreator
    ATTR_TABLE = SET_TO updatedatetime = @Value(UpdateTimeDate) @Value(UpdateTimeTime)
    -> DateFormatter

Bookmark: Date Formatting
DateFormatter
    FMT = %D
    SRCFMT = %Y%m%d
    INVALID_DATE_VALUE = _FME_NO_OP_
    DATE_ATTR = EndTimeDate,GIS_UPDATED,UpdateTimeDate,StartTimeDate
    -> DateFormatter_2
DateFormatter_2
    FMT = %I":"%M" "%p
    SRCFMT = %H%M%S
    INVALID_DATE_VALUE = _FME_NO_OP_
    DATE_ATTR = EndTimeTime,StartTimeTime,UpdateTimeTime
    -> AttributeCopier
AttributeCopier
    ATTR_TABLE:
      COPY StartTimeDate > StartDay
      COPY StartTimeDate > StartMonth
      COPY StartTimeDate > StartDate
      COPY EndTimeDate > EndDay
      COPY EndTimeDate > EndMonth
      COPY EndTimeDate > EndDate
    -> Extracts_Day_from_Date
Extracts_Day_from_Date: DateFormatter
    FMT = %A
    SRCFMT = Unknown - Automatic Detection
    INVALID_DATE_VALUE = _FME_NO_OP_
    DATE_ATTR = StartDay,EndDay
    -> Extracts_Month_from_Date
Extracts_Month_from_Date: DateFormatter
    FMT = %B
    SRCFMT = Unknown - Automatic Detection
    INVALID_DATE_VALUE = _FME_NO_OP_
    DATE_ATTR = EndMonth,StartMonth
    -> Date_Formatter_3
Date_Formatter_3: DateFormatter
    FMT = %d
    SRCFMT = Unknown - Automatic Detection
    INVALID_DATE_VALUE = _FME_NO_OP_
    DATE_ATTR = EndDate,StartDate
    -> Restriction_Height

Bookmark: Restriction Formatting
  Restriction Height																Restriction Axle																Restriction Weight																		Restriction Width
Restriction_Height: AttributeFilter
    ATTR_NAME = RestrictionHeight
    ATTR_VALUES = <EMPTY>,<MISSING>,<NULL>,<UNFILTERED>
    <EMPTY> -> Restriction_Axle
    <MISSING> -> Restriction_Axle
    <UNFILTERED> -> Restriction_Height_Calculation
Restriction_Height_Calculation: ExpressionEvaluator
    VAL_ATTR = Restriction Height
    ACTION = Create New Attribute
    EXPRESSION = @Value(RestrictionHeight)/30.48
    -> StringFormatter_2
StringFormatter_2
    FORMAT = .2f
    SRC_ATTRS = "Restriction Height"
    -> AttributeCreator
AttributeCreator
    ATTR_TABLE:
      SET_TO height2 = Height limit of @Value(Restriction Height) ft.
      SET_TO height1 = There is a height limit in effect.
    -> Restriction_Axle
Restriction_Axle: AttributeFilter
    ATTR_NAME = RestrictionWeightAxle
    ATTR_VALUES = <EMPTY>,<MISSING>,<NULL>,<UNFILTERED>
    <EMPTY> -> Restriction_Weight
    <MISSING> -> Restriction_Weight
    <UNFILTERED> -> Restriction_Axle_Weight_Calculation
Restriction_Axle_Weight_Calculation: ExpressionEvaluator
    VAL_ATTR = Restriction Axle Weight
    ACTION = Create New Attribute
    EXPRESSION = @Value(RestrictionWeightAxle)/0.4536
    -> StringFormatter_3
StringFormatter_3
    FORMAT = .0f
    SRC_ATTRS = "Restriction Axle Weight"
    -> AttributeCreator_2
AttributeCreator_2
    ATTR_TABLE:
      SET_TO axle2 = Axle weight limit @Value(Restriction Axle Weight) lbs.
      SET_TO axle1 = There is an axle load limit in effect.
    -> Restriction_Weight
Restriction_Weight: AttributeFilter
    ATTR_NAME = RestrictionWeightVehicle
    ATTR_VALUES = <EMPTY>,<MISSING>,<NULL>,<UNFILTERED>
    <EMPTY> -> Restriction_Width
    <MISSING> -> Restriction_Width
    <UNFILTERED> -> Restriction_Weight_Calculation
Restriction_Weight_Calculation: ExpressionEvaluator
    VAL_ATTR = Restriction Vehicle Weight
    ACTION = Create New Attribute
    EXPRESSION = @Value(RestrictionWeightVehicle)/0.4536
    -> StringFormatter_4
StringFormatter_4
    FORMAT = .0f
    SRC_ATTRS = "Restriction Vehicle Weight"
    -> AttributeCreator_3
AttributeCreator_3
    ATTR_TABLE:
      SET_TO weight1 = There is a weight limit in effect.
      SET_TO weight2 = No vehicles over @Value(Restriction Vehicle Weight) lbs.
    -> Restriction_Width
Restriction_Width: AttributeFilter
    ATTR_NAME = RestrictionWidth
    ATTR_VALUES = <EMPTY>,<MISSING>,<NULL>,<UNFILTERED>
    <EMPTY> -> ServiceAttributes
    <MISSING> -> ServiceAttributes
    <UNFILTERED> -> Restriction_Width_Calculation
Restriction_Width_Calculation: ExpressionEvaluator
    VAL_ATTR = Restriction Width
    ACTION = Create New Attribute
    EXPRESSION = @Value(RestrictionWidth)/30.48
    -> StringFormatter_5
StringFormatter_5
    FORMAT = .2f
    SRC_ATTRS = "Restriction Width"
    -> AttributeCreator_4
AttributeCreator_4
    ATTR_TABLE:
      SET_TO width1 = There is a weight limit in effect.
      SET_TO width2 = Width limit @Value(RestrictionWidth) ft.
    -> ServiceAttributes

Bookmark: Creates AGOL Feature Service Attributes
  Concatenates various headline, phrase, cause, restriction, and warning attributes into single attributes that are easier to work with.
ServiceAttributes: AttributeCreator
    ATTR_TABLE:
      SET_TO headline = @Value(hd_closure)@Value(hd_delay)@Value(hd_devicestat)@Value(hd_disaster)@Value(hd_disturbance)@Value(hd_incident)@Value(hd_mobsit)@Value(hd_obstruction)@Value(hd_parkinginfo)@Value(hd_pavementcond)@Value(hd_restriction)@Value(hd_roadwork)@Value(hd_specialevent)@Value(hd_sportsevent)@Value(hd_systeminfo)@Value(hd_traffic)@Value(hd_unusualdriving)@Value(hd_weather_cond)@Value(hd_winter_index)@Value(hd_winter_restriction)@Value(hd_wx_airquality)@Value(hd_wx_precip)@Value(hd_wx_temp)@Value(hd_wx_wind)
      SET_TO phrase = @Value(ph_closure)@Value(ph_delay)@Value(ph_devicestat)@Value(ph_disaster)@Value(ph_disturbance)@Value(ph_incident)@Value(ph_incident)@Value(ph_mobsit)@Value(ph_obstruction)@Value(ph_parkinginfo)@Value(ph_pavementcond)@Value(ph_restriction)@Value(ph_roadwork)@Value(ph_specialevent)@Value(ph_sportsevent)@Value(ph_systeminfo)@Value(ph_traffic)@Value(ph_unusualdriving)@Value(ph_weather_cond)@Value(ph_winter_index)@Value(ph_winter_restriction)@Value(ph_wx_airquality)@Value(ph_wx_precip)@Value(ph_wx_temp)@Value(ph_wx_wind)
      SET_TO cause = @Value(ca_closure)@Value(ca_delay)@Value(ca_devicestat)@Value(ca_disaster)@Value(ca_disturbance)@Value(ca_incident)@Value(ca_mobsit)@Value(ca_obstruction)@Value(ca_parkinginfo)@Value(ca_pavementcond)@Value(ca_restriction)@Value(ca_roadwork)@Value(ca_specialevent)@Value(ca_sportsevent)@Value(ca_systeminfo)@Value(ca_traffic)@Value(ca_unusualdriving)@Value(ca_weather_cond)@Value(ca_winter_index)@Value(ca_winter_restriction)@Value(ca_wx_airquality)@Value(ca_wx_precip)@Value(ca_wx_temp)@Value(ca_wx_wind).
      SET_TO restrictions = @Value(height1)@Value(width1)@Value(weight1)@Value(axle1)@Value(height2)@Value(width2)@Value(weight2)@Value(axle2)
      SET_TO Warnings = @Value(Warnings).
    -> PhraseWarningCaseChange
PhraseWarningCaseChange: StringCaseChanger
    ATTRLIST = Warnings phrase
    ATTRCHOICE = Selected Attributes
    CHANGE_TYPE = Title case
    -> HeadlineCaseChange
HeadlineCaseChange: StringCaseChanger
    ATTRLIST = headline
    ATTRCHOICE = Selected Attributes
    CHANGE_TYPE = Full Title Case
    -> Phrase

Bookmark: AGOL Phrase Filter/Creator
Phrase: TestFilter
    TEST_LIST:
      BOOL_OP,OR,COMPOSITE_TEST,<Unused>,TEST_CLAUSE,"TEST @Value(phrase) BEGINS_WITH
      TEST phrase ATTRIBUTE_VALUE_NULL """"
      TEST phrase ATTRIBUTE_IS_EMPTY """"
      TEST phr ATTRIBUTE_IS_MISSING """"",phrase
    DEFAULT_VALUE = <UNFILTERED>
    phrase -> PhraseCreatorN
    <UNFILTERED> -> Warnings
PhraseCreatorN: AttributeCreator
    ATTR_TABLE = SET_TO phrase = @Value(headline)
    -> Warnings

Bookmark: Warnings Filter/Creator
Warnings: TestFilter
    TEST_LIST:
      BOOL_OP,OR,COMPOSITE_TEST,<Unused>,TEST_CLAUSE,"TEST @Value(Warnings) BEGINS_WITH  .
      TEST @Value(Warnings) BEGINS_WITH .",Warning
    DEFAULT_VALUE = <UNFILTERED>
    Warning -> WarningsCreatorN
    <UNFILTERED> -> Cause
WarningsCreatorN: AttributeCreator
    ATTR_TABLE = SET_TO Warnings = FME_NULL_VALUE
    -> Cause

Bookmark: Cause Filter/Creator
Cause: TestFilter
    TEST_LIST:
      BOOL_OP,OR,COMPOSITE_TEST,<Unused>,TEST_CLAUSE,"TEST @Value(cause) BEGINS_WITH  .
      TEST @Value(cause) BEGINS_WITH .",cause
    DEFAULT_VALUE = <UNFILTERED>
    cause -> CauseCreatorN
    <UNFILTERED> -> CauseCreatorY
CauseCreatorN: AttributeCreator
    ATTR_TABLE = SET_TO cause = FME_NULL_VALUE
    -> WorkHours
CauseCreatorY: AttributeCreator
    ATTR_TABLE = SET_TO cause = due to @Value(cause)
    -> WorkHours

Bookmark: Work Hours Filter/Creator
WorkHours: TestFilter
    TEST_LIST:
      BOOL_OP,OR,COMPOSITE_TEST,<Unused>,TEST_CLAUSE,"TEST StartTimeTime ATTRIBUTE_IS_EMPTY """"
      TEST StartTimeTime ATTRIBUTE_VALUE_NULL """"
      TEST StartTimeTime ATTRIBUTE_IS_MISSING """"
      TEST EndTimeTime ATTRIBUTE_IS_MISSING """"
      TEST EndTimeTime ATTRIBUTE_IS_EMPTY """"
      TEST EndTimeTime ATTRIBUTE_VALUE_NULL """"",No Time
    DEFAULT_VALUE = <UNFILTERED>
    No Time -> WorkHoursCreatorN
    <UNFILTERED> -> WorkHoursCreatorY
WorkHoursCreatorN: AttributeCreator
    ATTR_TABLE = SET_TO WorkingHours = FME_NULL_VALUE
    -> EndDate
WorkHoursCreatorY: AttributeCreator
    ATTR_TABLE = SET_TO WorkingHours = Working hours are @Value(StartTimeTime) to @Value(EndTimeTime).
    -> EndDate

Bookmark: End Date Filter/Creator
EndDate: TestFilter
    TEST_LIST:
      BOOL_OP,OR,COMPOSITE_TEST,<Unused>,TEST_CLAUSE,"TEST EndDate ATTRIBUTE_IS_EMPTY """"
      TEST EndDate ATTRIBUTE_VALUE_NULL """"
      TEST EndDate ATTRIBUTE_IS_MISSING """"
      TEST @Value(MessageExpiryDate) > 20180000",No End Time
    DEFAULT_VALUE = <UNFILTERED>
    No End Time -> EndDateCreatorN
    <UNFILTERED> -> EndDateCreatorY
EndDateCreatorN: AttributeCreator
    ATTR_TABLE = SET_TO EndDate = FME_NULL_VALUE
    -> DirectionMerger [REQUESTOR]
EndDateCreatorY: AttributeCreator
    ATTR_TABLE = SET_TO EndDate = Until @Value(EndMonth) @Value(EndDate).
    -> DirectionMerger [REQUESTOR]

Bookmark: Add pretty Direction based on Route and LinkDirection
  Add Direction based on Route and LinkDirection (for roads in Iowa and other US Hwys/Interstates)
CSV (reader CSV_1)
    attributes: RouteDesignator char(15), LinkDirectionPositive char(11), LinkDirectionNegative char(11)
    -> DirectionMerger [SUPPLIER]
DirectionMerger: FeatureMerger
    GEOM_TYPE = Build Polygons
    PROCESS_DUPS = Yes
    SUPPLIERS_FIRST = No
    ATTR_CONFLICT_RES = Use Requestor
    MERGE_TYPE = Attributes Only
    ATTR_ACCUM_MODE = Merge Supplier
    JOIN_KEYS = @Value(RouteDesignator) @Value(RouteDesignator) AUTO
    REJECT_NULL_MISSING_KEYS = No
    CONNECT_Z_MODE = First Wins
    IGNORE_NULLS = No
    MERGED -> DirectionCreator
    NOT_MERGED -> DirectionCreator
DirectionCreator: AttributeCreator
    ATTR_TABLE = SET_TO Direction = FME_CONDITIONAL:DEFAULT_VALUE'_FME_NO_OP_'BOOL_OP;OR;COMPOSITE_TEST;<Unused>;TEST @Value(LinkDirection) = negative direction'@Value(LinkDirectionNegative)'BOOL_OP;OR;COMPOSITE_TEST;<Unused>;TEST @Value(LinkDirection) = positive direction'@Value(LinkDirectionPositive)'BOOL_OP;OR;COMPOSITE_TEST;<Unused>;TEST @Value(LinkDirection) = both directions'Both Directions'FME_NUM_CONDITIONS4___
    -> DirectionShortCreator
DirectionShortCreator: AttributeCreator
    ATTR_TABLE = SET_TO ShortDirection = FME_CONDITIONAL:DEFAULT_VALUE'_FME_NO_OP_'BOOL_OP;OR;COMPOSITE_TEST;<Unused>;TEST @Value(Direction) = Northbound' NB'BOOL_OP;OR;COMPOSITE_TEST;<Unused>;TEST @Value(Direction) = Southbound' SB'BOOL_OP;OR;COMPOSITE_TEST;<Unused>;TEST @Value(Direction) = Eastbound' EB'BOOL_OP;OR;COMPOSITE_TEST;<Unused>;TEST @Value(Direction) = Westbound' WB'FME_NUM_CONDITIONS5___
    -> RouteCreator
RouteCreator: AttributeCreator
    ATTR_TABLE = SET_TO RouteDesignator = @Value(RouteDesignator)@Value(ShortDirection)
    -> MsgTypeSorter

Bookmark: Headline and Message Creation
  This is where the real magic happens for formatting headlines and mesages
MsgTypeSorter: AttributeFilter
    ATTR_NAME = STYLE
    ATTR_VALUES = <EMPTY>,<MISSING>,<NULL>,<UNFILTERED>,future_event,restriction
    <UNFILTERED> -> GeneralHL_MSG
    future_event -> FutureHL_MSG
    restriction -> RestrictionHL_MSG
GeneralHL_MSG: AttributeCreator
    ATTR_TABLE:
      SET_TO headline = @Value(RouteDesignator): @Value(headline)
      SET_TO message = @Value(phrase)@Value(cause)@Value(Warnings)@Value(restrictions)@Value(WorkingHours) @Value(EndDate)
    -> ...MSGReplacer
FutureHL_MSG: AttributeCreator
    ATTR_TABLE:
      SET_TO headline = Starts @Value(StartDay) @Value(StartMonth) @Value(StartDate). @Value(RouteDesignator): @Value(headline)
      SET_TO message = @Value(phrase)@Value(cause)@Value(Warnings)@Value(restrictions)@Value(WorkingHours) ...
    -> ...MSGReplacer
RestrictionHL_MSG: AttributeCreator
    ATTR_TABLE:
      SET_TO headline = @Value(RouteDesignator): @Value(headline)
      SET_TO message = @Value(Warnings)@Value(restrictions)@Value(WorkingHours) @Value(EndDate)
    -> ...MSGReplacer

Bookmark: Message Formatting/Creation
  Final formatting and trimming of message and description attributes to go to AGOL
...MSGReplacer: StringReplacer
    FIND_TEXT = " ... "
    CASE = NO
    REPLACE_TEXT = " "
    NO_MATCH = _FME_NO_OP_
    SRC_ATTRS = message,Descriptions
    REGEXP = NO
    -> .MSGReplacer_2
.MSGReplacer_2: StringReplacer
    FIND_TEXT = " ."
    CASE = NO
    REPLACE_TEXT = " "
    NO_MATCH = _FME_NO_OP_
    SRC_ATTRS = message,Descriptions
    REGEXP = NO
    -> MSGTrimmer
MSGTrimmer: AttributeTrimmer
    TRIM_TYPE = Both
    TRIM_CHARS = " "
    TRIM_TO_NONE = Yes
    SRC_ATTRS = message,Descriptions
    -> MSG0Creator
MSG0Creator: SubstringExtractor
    SRC_STRING = @Value(message)
    START = 0
    END = 252
    RESULT_ATTR = msg0
    -> MSG1Creator
MSG1Creator: SubstringExtractor
    SRC_STRING = @Value(message)
    START = 253
    END = 506
    RESULT_ATTR = msg1
    -> DESC0Creator
DESC0Creator: SubstringExtractor
    SRC_STRING = @Value(Descriptions)
    START = 0
    END = 252
    RESULT_ATTR = Desc0
    -> DESC0Remover
DESC0Remover: StringPairReplacer
    CASE = no
    SRC_ATTR = Desc0
    MAP = "<a   /a>   href=\"   =  "
    RESULT_ATTR = Desc0
    -> DESC1Creator
DESC1Creator: SubstringExtractor
    SRC_STRING = @Value(Descriptions)
    START = 253
    END = 504
    RESULT_ATTR = Desc1
    -> DESC1Remover
DESC1Remover: StringPairReplacer
    CASE = no
    SRC_ATTR = Desc1
    MAP = "<a   /a>   href=\"   =  "
    RESULT_ATTR = Desc1
    -> MSG0Trimmer
MSG0Trimmer: AttributeTrimmer
    TRIM_TYPE = Left
    TRIM_CHARS = " "
    TRIM_TO_NONE = Yes
    SRC_ATTRS = Desc1,Desc0
    -> MSG1Trimmer
MSG1Trimmer: AttributeTrimmer
    TRIM_TYPE = Right
    TRIM_CHARS = " "
    TRIM_TO_NONE = Yes
    SRC_ATTRS = msg1,Desc1
    -> gisupdated

Bookmark: Adds Date of Last update, Editor to AGOL, and link text attributes
gisupdated: TimeStamper
    FMT = ^Y^m^d ^H^M^S
    TIME_ATTR = gisupdated
    -> Editor
Editor: AttributeCreator
    ATTR_TABLE = SET_TO Editor = IowaDOT_OTO
    -> Links
Links: AttributeCreator
    ATTR_TABLE = SET_TO linktxt = FME_CONDITIONAL:DEFAULT_VALUE'_FME_NO_OP_'BOOL_OP;OR;COMPOSITE_TEST;<Unused>;TEST @Value(ORGID) = Iowa'http://hb.511ia.org/#allReports/eventAlbum/@Value(ID)'FME_NUM_CONDITIONS2___
    -> AttributeRenamer

Bookmark: Renames and removes excess attributes
AttributeRenamer
    ATTR_TABLE:
      RENAME_SET_DEFAULT EndTimeDate > EndDate
      RENAME_SET_DEFAULT EndTimeTime > EndTime
      RENAME_SET_DEFAULT MessageExpiryDate > ExpireDate
      RENAME_SET_DEFAULT MessageExpiryTime > ExpireTime
      RENAME_SET_DEFAULT MessageIssueDate > IssueDate
      RENAME_SET_DEFAULT MessageIssueTime > IssueTime
      RENAME_SET_DEFAULT RouteDesignator > Route
      RENAME_SET_DEFAULT StartTimeDate > StartDate
      RENAME_SET_DEFAULT StartTimeTime > StartTime
      RENAME_SET_DEFAULT UpdateTimeDate > UpdateDate
      RENAME_SET_DEFAULT UpdateTimeTime > UpdateTime
      RENAME_SET_DEFAULT Instructions > Instruct
      RENAME_SET_DEFAULT restrictions > Restrict_
    -> AttributeRemover
AttributeRemover
    LIST_ATTRS = _matched_parts{}.part _matched_parts{}.startIndex
    REMOVE_ATTRS = hd_closure,EndDate,Status,ph_obstruction,StartTimeUTCoffset,width1,Longitude1,SpeedLimit,MessageIssueUTCoffset,height2,Descriptions,Update,hd_traffic,height1,ph_incident,Longitude2,ph_restriction,hd_obstruction,ph_delay,StartMonth,axle2,EndTimeUTCoffset,Latitude2,Restriction Vehicle Weight,ca_roadwork,WorkingHours,LinearReference2,Restriction Width,ca_specialevent,Restriction Axle Weight,EndDay,StartDay,EndMonth,Latitude1,UpdateTimeUTCoffset,ph_traffic,RestrictionHeight,_matched_characters,weight1,Ownership,hd_restriction,CrossRoad2,message,Warnings,hd_roadwork,ph_pavementcond,ca_restriction,weight2,hd_incident,RestrictionWeightAxle,StartDate,width2,ph_roadwork,ph_closure,LinearReference1,ca_obstruction,RestrictionLength,RestrictionWidth,CrossRoad1,MessageNumber,ph_wx_airquality,RestrictionWeightVehicle,axle1,Restriction Height,hd_specialevent
    -> STYLEFilter

Bookmark: CARS511 AGOL Feature Service Filter
STYLEFilter: AttributeFilter
    ATTR_NAME = STYLE
    ATTR_VALUES = <EMPTY>,<MISSING>,<NULL>,<UNFILTERED>,roadwork,restriction,future_event,closure,warning,lane_closure,priority_closure,priority_info,priority_warning,info
    <UNFILTERED> -> Iowa (writer GEODATABASE_FILE_1)
    roadwork -> Iowa (writer GEODATABASE_FILE_1)
    restriction -> Iowa (writer GEODATABASE_FILE_1)
    future_event -> Iowa (writer GEODATABASE_FILE_1)
    closure -> Iowa (writer GEODATABASE_FILE_1)
    warning -> Iowa (writer GEODATABASE_FILE_1)
    lane_closure -> Iowa (writer GEODATABASE_FILE_1)
    priority_closure -> Iowa (writer GEODATABASE_FILE_1)
    priority_info -> Iowa (writer GEODATABASE_FILE_1)
    priority_warning -> Iowa (writer GEODATABASE_FILE_1)
    info -> Iowa (writer GEODATABASE_FILE_1)

Bookmark: Writes to AGOL Feature Service - FGDB For Testing Purposes
  FGDB for testing/development purposes.
Iowa (writer GEODATABASE_FILE_1)
    attributes: OBJECTID integer, AltRoute char(254), EndTime char(254), ID char(254), ExpireDate char(254), ExpireTime char(254), IssueDate char(254), IssueTime char(254), Priority double, Route char(254), StartTime char(254), UpdateDate char(254), UpdateTime char(254), ORGID char(254), Instruct char(254), gisupdated char(254), STYLE char(254), headline char(254), phrase char(254), cause char(254), Restrict_ char(254), msg0 char(254), msg1 char(254), Desc0 char(254), Desc1 char(254), linktxt char(254), CreationDa date, Creator char(50), EditDate date, Editor char(50)

FME custom transformer DateDifferenceCalculator
Calculates the difference in time between two dates.
Input Ports
    Input
Any feature with with a start date and a end date attribute.
    Output Ports
    Output
All features with an additional date difference attribute.
    <Rejected>
Features are rejected if the any of the two date attributes are NULL, Missing or empty. The value MISSING_DATE_ATTRIBUTE is stored in the fme_rejection_code attribute.
    Parameters
    Input Date Format
Format of the date stored in the start date and the end date attribute. A detailed explanation of the date format strings can be found in the documentation of the DateFormatter.
    Output Time Units
The time units in which the date difference will be calculated.
    Name of Output Attribute
Name of the attribute that hold the calculated date difference.
    Start date
Attribute that holds the start date in the chosen Input Date Format.
    End date
Attribute that holds the end date in the chosen Input Date Format.

Parameters:
- Unit = 86400   # Output Time Units
- Output_Name = _TimeDifference   # Name of output attribute
- FMT = %Y%m%d   # Input Date Format
- StartDate =   # Start date
- EndDate =   # End date

INPUT (input)
    -> ParameterFetcher
ParameterFetcher
    ATTR_LIST = DDC_StartDate {$(StartDate)} DDC_EndDate {$(EndDate)}
    -> Tester
Tester
    TEST_MODE = Automatic
    TEST_CLAUSE:
      TEST @Value(DDC_StartDate) != ""
      TEST @Value(DDC_EndDate) != ""
      TEST DDC_StartDate NOT_ATTRIBUTE_VALUE_NULL ""
      TEST DDC_EndDate NOT_ATTRIBUTE_VALUE_NULL ""
      TEST DDC_StartDate NOT_ATTRIBUTE_IS_MISSING ""
      TEST DDC_EndDate NOT_ATTRIBUTE_IS_MISSING ""
    BOOL_OP = AND
    TEST_DESCRIPTION = ""
    PASSED -> DateFormatter
    FAILED -> AttributeCreator
    FAILED -> OUTPUT (output)
Note: Convert temp Date Attributes / to seconds since UNIX Epoch
DateFormatter
    FMT = %s
    SRCFMT = $(FMT)
    INVALID_DATE_VALUE = _FME_NO_OP_
    DATE_ATTR = DDC_StartDate,DDC_EndDate
    -> ExpressionEvaluator
Note: Subtract Dates and / convert to desired unit
ExpressionEvaluator
    VAL_ATTR = $(Output_Name)
    EXPRESSION = @round(1.0*(@Value(DDC_EndDate)-@Value(DDC_StartDate))/$(Unit))
    -> OUTPUT (output)
OUTPUT (output)
AttributeCreator
    ATTR_TABLE = SET_TO fme_rejection_code = MISSING_DATE_ATTRIBUTE
    -> <Rejected> (output)
<Rejected> (output)
