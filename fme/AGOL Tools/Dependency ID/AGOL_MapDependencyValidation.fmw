FME workspace AGOL_MapDependencyValidation.fmw
Title: AGOL Map Dependency Validation
Description: Workspace gets a list of publicly accessible web maps, gets the item data for each of the web maps, parses layer urls and calls each unique layer url to ensure that it is accessible (by returning an item count) and log it if it fails to return a count.
History: 20230922,drunneals,Version 1

Parameters:
- DestDataset_FFS =   # Destination FME Feature Store (FFS) File
- PortalURL =   # https Base URL
- PortalUserName =   # User
- PortalPassword =   # Password
- OrgID =   # AGOL Org ID

Writers:
- FFS_1: FFS to $(DestDataset_FFS)

Bookmark: Get Token
Creator
    GEOMTYPE = Geometry Object
    NUM = 1
    CREATED -> HTTPCaller_2
Note: Generate token
HTTPCaller_2
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    MULTIPARTS = f StringUpload SOURCE_EXPRESSION;json;MIME_TYPE;text/plain;FME_CONTROLLER_QUERY_FILE;transformers/dependencies/http/StringUpload.fme;FME_CONTROLLER_CHOICE;StringUpload username StringUpload SOURCE_EXPRESSION;$(PortalUserName);MIME_TYPE;text/plain;FME_CONTROLLER_QUERY_FILE;transformers/dependencies/http/StringUpload.fme;FME_CONTROLLER_CHOICE;StringUpload password StringUpload SOURCE_EXPRESSION;$(PortalPassword);MIME_TYPE;text/plain;FME_CONTROLLER_QUERY_FILE;transformers/dependencies/http/StringUpload.fme;FME_CONTROLLER_CHOICE;StringUpload referer StringUpload SOURCE_EXPRESSION;$(PortalURL);MIME_TYPE;text/plain;FME_CONTROLLER_QUERY_FILE;transformers/dependencies/http/StringUpload.fme;FME_CONTROLLER_CHOICE;StringUpload expiration StringUpload SOURCE_EXPRESSION;60;MIME_TYPE;text/plain;FME_CONTROLLER_QUERY_FILE;transformers/dependencies/http/StringUpload.fme;FME_CONTROLLER_CHOICE;StringUpload
    RATE_LIMIT_INTERVAL_IN_SECONDS = 60
    RATE_LIMIT_MAX_REQUESTS = 1
    RATE_LIMIT_REQUEST_TIMING = BURST
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(PortalURL)/sharing/generateToken
    TRANSFER_TIMEOUT_LENGTH = 90
    UPLOAD_TYPE = Multipart / Form Data
    USE_COOKIES = No
    VERIFY_SSL_CERTIFICATES = Yes
    -> JSONFlattener_3
JSONFlattener_3
    ERROR_LIST_ATTR = _json_error
    JSON_DOCUMENT = @Value(_response_body)
    NEW_ATTRIBUTES = token
    READ_FROM_FILE = NO
    RECURSIVE = Yes
    -> GetAGOLMapItems

Bookmark: Get Map Data
GetAGOLMapItems: GetAGOLItems
    OrgID = $(OrgID)
    PortalURL = $(PortalURL)
    token = @Value(token)
    Maps -> QueryMapData
    Layers -> HTTPCaller_4
QueryMapData: HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(PortalURL)/sharing/rest/content/items/@Value(id)/data?f=json&token=@Value(token)
    TRANSFER_TIMEOUT_LENGTH = 90
    USE_COOKIES = No
    VERIFY_SSL_CERTIFICATES = Yes
    -> FilterEsriMapsOut
FilterEsriMapsOut: Tester
    BOOL_OP = OR
    TEST_CLAUSE = CASE_INSENSITIVE_TEST @Value(owner) BEGINS_WITH esri
    TEST_MODE = CASE_INSENSITIVE_TEST
    FAILED -> JSONFlattener
JSONFlattener
    ERROR_LIST_ATTR = _json_error
    JSON_DOCUMENT = @Value(_response_body)
    NEW_ATTRIBUTES = operationalLayers{}.url authoringAppVersion version layers{}.url layerType description numViews access
    READ_FROM_FILE = NO
    RECURSIVE = Yes
    -> AttributeManager_2
AttributeManager_2
    ATTR_TABLE:
      REMOVE _creation_instance (uint64)
      RENAME_SET_VALUE id > Map.id (buffer)
      RENAME_SET_VALUE title > Map.title (buffer)
      RENAME_SET_VALUE owner > Map.owner (buffer)
      REMOVE _response_body (buffer)
      REMOVE _http_status_code (buffer)
      RENAME_SET_VALUE authoringAppVersion > Map.authoringAppVersion (buffer)
      RENAME_SET_VALUE version > Map.version (buffer)
      RENAME_SET_VALUE description > Map.description (buffer)
      RENAME_SET_VALUE numViews > Map.numViews (buffer)
      RENAME_SET_VALUE access > Map.access (buffer)
    -> ListExploder

Bookmark: Query Map Data JSON to get layer URLs
ListExploder
    ATTR_ACCUM_MODE = Merge List Attributes
    ATTR_CONFLICT_RES = Use List Attribute Values
    INDEX_ATTR = _element_index
    LIST_ATTR = operationalLayers{}
    ELEMENTS -> Tester_3
    <REJECTED> -> BasemapsOrFeatureCollections
Tester_3
    BOOL_OP = OR
    TEST_CLAUSE = TEST url ATTRIBUTE_HAS_A_VALUE ""
    TEST_MODE = TEST
    PASSED -> AttributeManager_4
    FAILED -> ListExploder_4
ListExploder_4
    ATTR_ACCUM_MODE = Merge List Attributes
    ATTR_CONFLICT_RES = Use List Attribute Values
    INDEX_ATTR = _element_index
    LIST_ATTR = layers{}
    ELEMENTS -> AttributeManager_4
    <REJECTED> -> BasemapsOrFeatureCollections
AttributeManager_4
    ATTR_TABLE:
      RENAME_SET_VALUE url > Service.url (buffer)
      REMOVE _element_index (uint32)
    USER_EXPOSED_ATTRIBUTES = version,authoringAppVersion,owner,title
    -> TestFilter_2
TestFilter_2
    DEFAULT_VALUE = Other Services
    PASSED_TEST_GROUP_OUTPUT = FIRST
    TEST_LIST:
      "BOOL_OP,OR,COMPOSITE_TEST,""""""1 OR 2 OR 3"""""",TEST_CLAUSE,TEST Service.url ATTRIBUTE_VALUE_NULL ""
      TEST Service.url ATTRIBUTE_IS_EMPTY ""
      TEST Service.url ATTRIBUTE_IS_MISSING """,No Service URL,"BOOL_OP,OR,COMPOSITE_TEST,""""""1"""""",TEST_CLAUSE,CASE_INSENSITIVE_TEST @Value(Service.url) BEGINS_WITH https://utility.arcgis.com/usrsvcs/servers/",Proxy Service
    Proxy Service -> FeatureMerger_4 [REQUESTOR]
    Other Services -> FeatureMerger_4 [REQUESTOR]
BasemapsOrFeatureCollections: Inspector [off]
AttributeManager_9
    ATTR_TABLE:
      REMOVE layerType (buffer)
      REMOVE layers{}.url (buffer)
      REMOVE Map.id (buffer)
      REMOVE Map.title (buffer)
      REMOVE Map.owner (buffer)
      REMOVE Map.authoringAppVersion (buffer)
      REMOVE Map.version (buffer)
      REMOVE Map.description (buffer)
      REMOVE Map.numViews (buffer)
      REMOVE Map.access (buffer)
    -> DuplicateFilter
DuplicateFilter
    INPUT_ORDERED_CHOICE = No
    KEYATTR = Service.id Service.url
    UNIQUE -> Tester
Tester
    BOOL_OP = OR
    TEST_CLAUSE = TEST @Right(@Value(Service.url),1) TYPE INT
    TEST_MODE = TEST
    PASSED -> QueryLayer
    FAILED -> AttributeManager
AttributeManager
    ATTR_TABLE:
      SET_TO OrgURL (varchar(200)) = $(PortalURL)
      SET_TO Service.comment (buffer) = WARNING: This Service was not tested due to not having a layer ID associated with the service url.
      REMOVE token (buffer)
    -> ServicesWithoutLayerID
    -> ServicesUsedInMapWarningsErrors (writer FFS_1)
ServicesWithoutLayerID: Inspector [off]

Bookmark: Get Proxy Services
HTTPCaller_4
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(PortalURL)/sharing/rest/content/items/@Value(id)?f=json&token=@Value(token)
    TRANSFER_TIMEOUT_LENGTH = 90
    USE_COOKIES = No
    VERIFY_SSL_CERTIFICATES = Yes
    -> JSONFlattener_5
JSONFlattener_5
    ERROR_LIST_ATTR = _json_error
    JSON_DOCUMENT = @Value(_response_body)
    NEW_ATTRIBUTES = title description url sourceUrl numViews owner access type
    READ_FROM_FILE = NO
    RECURSIVE = Yes
    -> AttributeManager_8
AttributeManager_8
    ATTR_TABLE:
      REMOVE _creation_instance (uint64)
      REMOVE _response_body (buffer)
      REMOVE _http_status_code (buffer)
      REMOVE token (buffer)
      SET_TO ItemURL (varchar(200)) = $(PortalURL)/home/item.html?id=@Value(id)
    -> TestFilter
TestFilter
    DEFAULT_VALUE = Other Layers
    PASSED_TEST_GROUP_OUTPUT = FIRST
    TEST_LIST:
      "BOOL_OP,OR,COMPOSITE_TEST,""""""1"""""",TEST_CLAUSE,TEST @Value(type) = Service Definition",SD,"BOOL_OP,AND,COMPOSITE_TEST,""""""1 AND 2"""""",TEST_CLAUSE,CASE_INSENSITIVE_TEST @Value(url) BEGINS_WITH https://utility.arcgis.com/usrsvcs/servers/
      TEST sourceUrl ATTRIBUTE_IS_MISSING """,Shared item created from proxy,"BOOL_OP,AND,COMPOSITE_TEST,""""""1 AND 2"""""",TEST_CLAUSE,CASE_INSENSITIVE_TEST @Value(url) BEGINS_WITH https://utility.arcgis.com/usrsvcs/servers/
      TEST sourceUrl ATTRIBUTE_HAS_A_VALUE """,Proxy Item
    Shared item created from proxy -> AttributeSplitter
    Proxy Item -> BulkAttributeRenamer
    Other Layers -> BulkAttributeRenamer_3
AttributeSplitter
    ATTR_NAME = url
    DELIMITER = /
    DROP_EMPTY_PARTS = No
    LIST_NAME = _list
    TRIM_OPTION = Both
    -> AttributeManager_7
AttributeManager_7
    ATTR_TABLE:
      RENAME_SET_VALUE ItemURL > Service.ItemURL (varchar(200))
      RENAME_SET_VALUE id > Service.id (buffer)
      RENAME_SET_VALUE title > Service.title (buffer)
      RENAME_SET_VALUE owner > Service.owner (buffer)
      RENAME_SET_VALUE description > Service.description (buffer)
      RENAME_SET_VALUE url > Service.url (buffer)
      RENAME_SET_VALUE sourceUrl > Service.sourceUrl (buffer)
      RENAME_SET_VALUE numViews > Service.numViews (buffer)
      RENAME_SET_VALUE access > Service.access (buffer)
      SET_TO Proxy.id (varchar(200)) = @Value(_list{5})
      RENAME_SET_VALUE type > Service.type (buffer)
      REMOVE _list{} (varchar(200))
    -> FeatureMerger_3 [REQUESTOR]
BulkAttributeRenamer
    ATTRCHOICE = All Attributes
    MODE_CHOICE = RENAME
    PATTERN_ACTION_DISP = ADDPREFIX
    REPLACE_STR = Proxy.
    -> FeatureMerger_3 [SUPPLIER]
FeatureMerger_3
    ATTR_ACCUM_MODE = Merge Supplier
    ATTR_CONFLICT_RES = Use Requestor
    IGNORE_NULLS = No
    JOIN_KEYS = @Value(Proxy.id) @Value(Proxy.id) AUTO
    MERGE_TYPE = Attributes Only
    PROCESS_DUPS = NO
    REJECT_NULL_MISSING_KEYS = No
    SUPPLIERS_FIRST = No
    MERGED -> DuplicateFilter_3
    UNUSED_SUPPLIER -> BulkAttributeRenamer_2
BulkAttributeRenamer_2
    ATTRCHOICE = All Attributes
    CASE_DISP = YES
    MODE_CHOICE = RENAME
    PATTERN_ACTION_DISP = STRINGREPLACE
    REPLACE_PATTERN = Proxy.
    REPLACE_STR = Service.
    -> DuplicateFilter_3
BulkAttributeRenamer_3
    ATTRCHOICE = All Attributes
    MODE_CHOICE = RENAME
    PATTERN_ACTION_DISP = ADDPREFIX
    REPLACE_STR = Service.
    -> DuplicateFilter_3
DuplicateFilter_3
    INPUT_ORDERED_CHOICE = No
    KEYATTR = Service.url
    UNIQUE -> AttributeManager_10
AttributeManager_10
    ATTR_TABLE = SET_TO ProxyService (varchar(200)) = FME_CONDITIONAL:DEFAULT_VALUE'N'BOOL_OP;OR;COMPOSITE_TEST;1 OR 2;CASE_INSENSITIVE_TEST @Value(Proxy.url) BEGINS_WITH https://utility.arcgis.com/usrsvcs/servers/;CASE_INSENSITIVE_TEST @Value(Service.url) BEGINS_WITH https://utility.arcgis.com/usrsvcs/servers/'Y'FME_NUM_CONDITIONS2___
    -> FeatureMerger_4 [SUPPLIER]
FeatureMerger_4
    ATTR_ACCUM_MODE = Merge Supplier
    ATTR_CONFLICT_RES = Use Supplier
    IGNORE_NULLS = No
    JOIN_KEYS = @Value(Service.url) @Value(Service.url) AUTO
    MERGE_TYPE = Attributes Only
    PROCESS_DUPS = NO
    REJECT_NULL_MISSING_KEYS = No
    SUPPLIERS_FIRST = No
    MERGED -> AttributeManager_14
    MERGED -> AttributeManager_9
    MERGED -> FeatureMerger [REQUESTOR]
    UNMERGED_REQUESTOR -> FeatureMerger [REQUESTOR]
    UNMERGED_REQUESTOR -> AttributeManager_9
    UNMERGED_REQUESTOR -> AttributeManager_14
    UNUSED_SUPPLIER -> AttributeManager_13
AttributeManager_14
    ATTR_TABLE:
      SET_TO OrgURL (varchar(200)) = $(PortalURL)
      SET_TO ServiceUsedInMap (buffer) = Y
      REMOVE token (buffer)
      REMOVE layerType (buffer)
      REMOVE layers{}.url (buffer)
    -> ServiceItems (writer FFS_1)
AttributeManager_13
    ATTR_TABLE:
      SET_TO OrgURL (varchar(200)) = $(PortalURL)
      SET_TO ServiceUsedInMap (buffer) = N
    -> ServiceItems (writer FFS_1)
ServiceItems (writer FFS_1)
    attributes: OrgURL varchar(200), ServiceUsedInMap buffer, ProxyService varchar(200), Map.id buffer, Map.title buffer, Map.owner buffer, Map.authoringAppVersion buffer, Map.version buffer, Map.description buffer, Map.numViews buffer, Map.access buffer, Service.ItemURL varchar(200), Service.id buffer, Service.title buffer, Service.description buffer, Service.owner buffer, Service.url buffer, Service.sourceUrl buffer, Service.numViews buffer, Service.access buffer, Service.type buffer, Proxy.ItemURL varchar(200), Proxy.id varchar(200), Proxy.title buffer, Proxy.description buffer, Proxy.owner buffer, Proxy.url buffer, Proxy.sourceUrl buffer, Proxy.numViews buffer, Proxy.access buffer,
      Proxy.type buffer

Bookmark: Query Layer - Validate response
QueryLayer: HTTPCaller
    CONNECTION_TIMEOUT_LENGTH = 60
    ERROR_ATTR = _error
    FOLLOW_REDIRECTS = DO_NOT_FOLLOW
    HTTP_METHOD = GET
    MAX_HTTP_VERSION = HTTP_2
    MAX_TRANSFERS_IN_PROGRESS = 25
    MINIMUM_ENCRYPTION_LEVEL = OS_DEFAULT
    RATE_LIMIT_INTERVAL_IN_SECONDS = 1
    RATE_LIMIT_MAX_REQUESTS = 5
    RATE_LIMIT_REQUEST_TIMING = BURST
    RESPONSE_TYPE = Attribute
    SPLIT_MULTIPART_DOWNLOADS = NO
    STATUS_CODE_ATTR = _http_status_code
    TARGET_ATTR = _response_body
    TARGET_ATTR_ENCODING = auto-detect
    TARGET_URL = @Value(Service.url)/query?where=1%3D1&returnCountOnly=true&f=pjson&token=@Value(token)
    TRANSFER_TIMEOUT_LENGTH = 90
    USE_COOKIES = No
    VERIFY_SSL_CERTIFICATES = Yes
    -> Tester_2
    <REJECTED> -> AttributeManager_3
Tester_2
    BOOL_OP = OR
    TEST_CLAUSE = CASE_INSENSITIVE_TEST @Value(_response_body) CONTAINS error
    TEST_MODE = CASE_INSENSITIVE_TEST
    PASSED -> AttributeManager_5
    FAILED -> SuccessfulServices
AttributeManager_5
    ATTR_TABLE:
      SET_TO OrgURL (varchar(200)) = $(PortalURL)
      SET_TO Service.comment (varchar(200)) = ERROR: There is most likely an issue with the service. It may not be shared publicly.
        @Value(_http_status_code): @Value(_response_body)
      REMOVE _response_body (buffer)
      REMOVE _http_status_code (buffer)
      REMOVE token (buffer)
    -> ServiceError
    -> FeatureMerger [SUPPLIER]
    -> ServicesUsedInMapWarningsErrors (writer FFS_1)
ServiceError: Inspector [off]
SuccessfulServices: Inspector [off]
AttributeManager_3
    ATTR_TABLE:
      SET_TO OrgURL (varchar(200)) = $(PortalURL)
      SET_TO Service.comment (varchar(200)) = ERROR: There is most likely an issue with the URL of the service. It may not exist or be a local url not accessible externally.
        @Value(_http_status_code): @Value(_response_body)
      REMOVE _error (buffer)
      REMOVE fme_rejection_code (buffer)
      REMOVE _response_body (buffer)
      REMOVE _http_status_code (buffer)
      REMOVE token (buffer)
    USER_EXPOSED_ATTRIBUTES = MapID
    -> ServerURLError
    -> FeatureMerger [SUPPLIER]
    -> ServicesUsedInMapWarningsErrors (writer FFS_1)
ServerURLError: Inspector [off]
ServicesUsedInMapWarningsErrors (writer FFS_1)
    attributes: OrgURL varchar(200), Service.comment buffer, Service.ItemURL varchar(200), Service.id buffer, Service.title buffer, Service.description buffer, Service.owner buffer, Service.url buffer, Service.sourceUrl buffer, Service.numViews buffer, Service.access buffer, Service.type buffer, Proxy.ItemURL varchar(200), Proxy.id varchar(200), Proxy.title buffer, Proxy.description buffer, Proxy.owner buffer, Proxy.url buffer, Proxy.sourceUrl buffer, Proxy.numViews buffer, Proxy.access buffer, Proxy.type buffer, ProxyService varchar(200), url buffer

Bookmark: Merge Layer URLs back together to Map Item Info
FeatureMerger
    ATTR_ACCUM_MODE = Merge Supplier
    ATTR_CONFLICT_RES = Use Requestor
    IGNORE_NULLS = No
    JOIN_KEYS = @Value(Service.url) @Value(Service.url) AUTO
    MERGE_TYPE = Attributes Only
    PROCESS_DUPS = NO
    REJECT_NULL_MISSING_KEYS = No
    SUPPLIERS_FIRST = No
    MERGED -> AttributeManager_12
    MERGED -> MapsWithErrors
    UNMERGED_REQUESTOR -> AttributeManager_11
MapsWithErrors: Inspector [off]
AttributeManager_12
    ATTR_TABLE:
      SET_TO Map.ItemURL (varchar(200)) = $(PortalURL)/home/item.html?id=@Value(Map.id)
      REMOVE token (buffer)
      REMOVE layerType (buffer)
      REMOVE layers{}.url (buffer)
    -> MapsWithServiceErrors (writer FFS_1)
MapsWithServiceErrors (writer FFS_1)
    attributes: Map.ItemURL varchar(200), Map.id buffer, Map.title buffer, Map.description buffer, Map.owner buffer, Map.numViews buffer, Map.access buffer, Map.authoringAppVersion buffer, Map.version buffer, Service.ItemURL varchar(200), Service.comment varchar(200), Service.id buffer, Service.title buffer, Service.description buffer, Service.owner buffer, Service.url buffer, Service.sourceUrl buffer, Service.numViews buffer, Service.access buffer, Service.type buffer, Proxy.ItemURL varchar(200), Proxy.id varchar(200), Proxy.title buffer, Proxy.description buffer, Proxy.owner buffer, Proxy.url buffer, Proxy.sourceUrl buffer, Proxy.numViews buffer, Proxy.access buffer, Proxy.type buffer,
      ProxyService varchar(200), OrgURL varchar(200), url buffer
AttributeManager_11
    ATTR_TABLE:
      SET_TO Map.ItemURL (varchar(200)) = $(PortalURL)/home/item.html?id=@Value(Map.id)
      REMOVE token (buffer)
      REMOVE layerType (buffer)
      REMOVE layers{}.url (buffer)
    -> MapsWithServices (writer FFS_1)
MapsWithServices (writer FFS_1)
    attributes: Map.ItemURL varchar(200), Map.id buffer, Map.title buffer, Map.description buffer, Map.owner buffer, Map.numViews buffer, Map.access buffer, Map.authoringAppVersion buffer, Map.version buffer, Service.ItemURL varchar(200), Service.id buffer, Service.title buffer, Service.description buffer, Service.owner buffer, Service.url buffer, Service.sourceUrl buffer, Service.numViews buffer, Service.access buffer, Service.type buffer, Proxy.ItemURL varchar(200), Proxy.id varchar(200), Proxy.title buffer, Proxy.description buffer, Proxy.owner buffer, Proxy.url buffer, Proxy.sourceUrl buffer, Proxy.numViews buffer, Proxy.access buffer, Proxy.type buffer, ProxyService varchar(200)

Bookmark: Not Used -- Identify POTENTIALLY unused services on AGOL - This is for informational use only. Keep data open even if you aren't using it, someone else might :) Also remember this only accounts for AGOL maps.
StringReplacer
    CASE = NO
    FIND_TEXT = /FeatureServer/\d*
    NO_MATCH = _FME_NO_OP_
    REGEXP = YES
    REPLACE_TEXT = /FeatureServer
    SRC_ATTRS = url
    -> StringCaseChanger_2
StringCaseChanger_2
    ATTRCHOICE = Selected Attributes
    ATTRLIST = url
    CHANGE_TYPE = lowercase
    -> DuplicateFilter_2
DuplicateFilter_2
    INPUT_ORDERED_CHOICE = No
    KEYATTR = url
    UNIQUE -> FeatureMerger_2 [SUPPLIER]
Note: Need to go into folders
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(PortalURL)/server/rest/services/?f=json&token=@Value(token)
    TRANSFER_TIMEOUT_LENGTH = 90
    USE_COOKIES = No
    VERIFY_SSL_CERTIFICATES = Yes
    -> JSONFlattener_2
JSONFlattener_2
    ERROR_LIST_ATTR = _json_error
    JSON_DOCUMENT = @Value(_response_body)
    NEW_ATTRIBUTES = services{}.name folders{} services{}.type
    READ_FROM_FILE = NO
    RECURSIVE = Yes
    -> ListExploder_2
    -> ListExploder_3
ListExploder_3
    ATTR_ACCUM_MODE = Merge List Attributes
    ATTR_CONFLICT_RES = Use List Attribute Values
    INDEX_ATTR = _element_index
    LIST_ATTR = folders{}
    ELEMENTS -> ListExploder_2
ListExploder_2
    ATTR_ACCUM_MODE = Merge List Attributes
    ATTR_CONFLICT_RES = Use List Attribute Values
    INDEX_ATTR = _element_index
    LIST_ATTR = services{}
    ELEMENTS -> StringCaseChanger
StringCaseChanger
    ATTRCHOICE = Selected Attributes
    ATTRLIST = name
    CHANGE_TYPE = lowercase
    -> FeatureMerger_2 [REQUESTOR]
FeatureMerger_2
    ATTR_ACCUM_MODE = Merge Supplier
    ATTR_CONFLICT_RES = Use Requestor
    IGNORE_NULLS = No
    JOIN_KEYS = @Value(url) @Value(url) STRING
    MERGE_TYPE = Attributes Only
    PROCESS_DUPS = NO
    REJECT_NULL_MISSING_KEYS = No
    SUPPLIERS_FIRST = No
    UNMERGED_REQUESTOR -> AttributeManager_6
AttributeManager_6
    ATTR_TABLE:
      REMOVE _creation_instance (uint64)
      REMOVE _response_body (buffer)
      REMOVE _http_status_code (buffer)
      REMOVE _element_index (uint32)
    -> unusedAGOLservices (writer FFS_1)
unusedAGOLservices (writer FFS_1)
    attributes: url buffer, name buffer, folders{} buffer, type buffer, folders buffer

FME custom transformer GetAGOLItems

Parameters:
- PortalURL =   # Portal URL
- OrgID =   # Enter Text Data
- token =

Input (input)
    -> AttributeManager
AttributeManager
    ATTR_TABLE = SET_TO nextStart (uint64) = 1
    -> HTTPCaller_2
    -> HTTPCaller_3
LoopInput (input)
    -> HTTPCaller_2
Looper2 (input)
    -> HTTPCaller_3
Layers (output)
Looper2 (output)

Bookmark: Maps Only
HTTPCaller_2
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(PortalURL)/sharing/rest/search?num=100&start=@Value(nextStart)&sortField=relevance&sortOrder=desc&q=orgid%3A$(OrgID)%20type%3A%22Web%20Map%22&f=json&token=$(token)
    TRANSFER_TIMEOUT_LENGTH = 90
    USE_COOKIES = No
    VERIFY_SSL_CERTIFICATES = Yes
    -> JSONFlattener_2
    -> JSONExtractor
JSONFlattener_2
    ERROR_LIST_ATTR = _json_error
    JSON_DOCUMENT = @Value(_response_body)
    NEW_ATTRIBUTES = results{}.id results{}.title results{}.owner
    READ_FROM_FILE = NO
    RECURSIVE = Yes
    -> ListExploder_2
ListExploder_2
    ATTR_ACCUM_MODE = Merge List Attributes
    ATTR_CONFLICT_RES = Use List Attribute Values
    INDEX_ATTR = _element_index
    LIST_ATTR = results{}
    ELEMENTS -> Maps (output)
Maps (output)
JSONExtractor
    EXTRACT_QUERY_TABLE = nextStart json["nextStart"]
    JSON_DOCUMENT = @Value(_response_body)
    READ_FROM_FILE = NO
    EVALUATED -> Tester
Tester
    BOOL_OP = OR
    TEST_CLAUSE = TEST @Value(nextStart) > 0
    TEST_MODE = TEST
    PASSED -> LoopInput (output)
LoopInput (output)

Bookmark: Layers
HTTPCaller_3
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(PortalURL)/sharing/rest/search?num=100&start=@Value(nextStart)&sortField=relevance&sortOrder=desc&q=orgid%3A$(OrgID)%20(type%3A%22Layer%22%20OR%20type%3A%22Feature%20Service%22%20OR%20type%3A%22Map%20Service%22%20OR%20type%3A%22Image%20Service%22%20OR%20type%3A%22WMS%22%20OR%20type%3A%22WFS%22%20OR%20type%3A%22WMTS%22%20OR%20type%3A%22KML%22%20OR%20type%3A%22Group%20Layer%22%20OR%20type%3A%22CSV%22%20OR%20type%3A%22Shapefile%22%20OR%20type%3A%22GeoJson%22%20OR%20type%3A%22Service%20Definition%22%20OR%20type%3A%22File%20Geodatabase%22%20)&f=json&token=$(token)
    TRANSFER_TIMEOUT_LENGTH = 90
    USE_COOKIES = No
    VERIFY_SSL_CERTIFICATES = Yes
    -> JSONFlattener_3
    -> JSONExtractor_2
JSONFlattener_3
    ERROR_LIST_ATTR = _json_error
    JSON_DOCUMENT = @Value(_response_body)
    NEW_ATTRIBUTES = results{}.id results{}.title results{}.owner
    READ_FROM_FILE = NO
    RECURSIVE = Yes
    -> ListExploder_3
ListExploder_3
    ATTR_ACCUM_MODE = Merge List Attributes
    ATTR_CONFLICT_RES = Use List Attribute Values
    INDEX_ATTR = _element_index
    LIST_ATTR = results{}
    ELEMENTS -> Layers (output)
JSONExtractor_2
    EXTRACT_QUERY_TABLE = nextStart json["nextStart"]
    JSON_DOCUMENT = @Value(_response_body)
    READ_FROM_FILE = NO
    EVALUATED -> Tester_2
Tester_2
    BOOL_OP = OR
    TEST_CLAUSE = TEST @Value(nextStart) > 0
    TEST_MODE = TEST
    PASSED -> Looper2 (output)
