FME workspace AGOLUsage.fmw
Title: AGOL Usage Stats Pull
Description: Job pulls AGOL Service usage stats and Data Store Performance.
History: 20230922,drunneals,Version 1

Parameters:
- EPOCH_Start =   # startTime
- EPOCH_End =   # endTime
- RESTServiceHive = services5   # REST Service Directory Hive
- DestDataset_FFS = /Users/Zipster/Desktop/Usage.ffs   # Destination FME Feature Store (FFS) File
- TOKEN:   # Python Script
      #-------------------------------------------------------------------------------
      # Name:        Truncates Data from REST Service prior to write
      # Purpose:     Ensures that REST service gets truncated, even when there is no data coming through the feed.
      #
      # Author:      Kelly Gerrow/David Runneals
      #Contact:      kgerrow@esri.com
      #
      # Created:     11/18/2015
      #-------------------------------------------------------------------------------
      
      def getToken(adminUser, pw):
              data = {'username': adminUser,
                  'password': pw,
                  'referer' : 'https://www.arcgis.com',
                  'f': 'json'}
              url  = 'https://arcgis.com/sharing/rest/generateToken'
              jres = requests.post(url, data=data, verify=False).json()
              return jres['token'],jres['ssl']
      
      #generates account information
      def GetAccount(pref, tokenfun):
          URL= pref+'www.arcgis.com/sharing/rest/portals/self?f=json&token=' + tokenfun
          response = requests.get(URL, verify=False)
          jres = json.loads(response.text)
          return jres['urlKey']
      
      import requests, json
      
      #Enter Username and Password
      user= "YOUR USERNAME HERE!" #raw_input('What is the ArcGIS Online Username?')
      pw = "YOUR PASSWORD HERE!" #raw_input('What is the ArcGIS Online Password?')
      
      #get account information
      token= getToken(user, pw)
      if token[1] == False:
                 pref='http://'
      else:
                 pref='https://'
      
      #Create Portal URL
      t=GetAccount(pref,token[0])
      portalUrl=pref+t
      
      return token[0]

Writers:
- FFS_1: FFS to $(DestDataset_FFS)

Note: To Use: / 1) Determine what the organizations REST service URL is and put the services # into the RestServiceHive parameter. / 2) Update line 30 & 31 of the Token Parameter with the Username/Password of an admin user in the organization. / 3) Run
Creator
    GEOMTYPE = Geometry Object
    NUM = 1
    CREATED -> AttributeManager_6

Bookmark: Get urlKey and id
AttributeManager_6
    ATTR_TABLE = SET_TO Token (varchar(200)) = $(TOKEN)
    -> GetOrgProperties [INITIATOR]
GetOrgProperties: FeatureReader
    ATTRIBUTES = JSONFeature,"2DStylesGroupQuery,access,allSSL,analysisLayersGroupQuery,availableCredits,basemapGalleryGroupQuery,canListApps,canListConsultingServices,canListData,canListPreProvisionedItems,canListSolutions,canProvisionDirectPurchase,canSearchPublic,canSetCustomBuyLink,canSetQuestionnaire,canSharePublic,canSignInArcGIS,canSignInIDP,canSignInOIDC,canSignInSocial,colorSetsGroupQuery,commentsEnabled,contentCategorySetsGroupQuery,created,culture,cultureFormat,customBaseUrl,databaseQuota,databaseUsage,defaultBasemap.baseMapLayers{}.url,defaultBasemap.baseMapLayers{}.layerType,defaultBasemap.baseMapLayers{}.resourceInfo.currentVersion,defaultBasemap.baseMapLayers{}.resourceInfo.mapName,defaultBasemap.baseMapLayers{}.resourceInfo.supportsDynamicLayers,defaultBasemap.baseMapLayers{}.resourceInfo.layers{}.id,defaultBasemap.baseMapLayers{}.resourceInfo.layers{}.name,defaultBasemap.baseMapLayers{}.resourceInfo.layers{}.parentLayerId,defaultBasemap.baseMapLayers{}.resourceInfo.layers{}.defaultVisibility,defaultBasemap.baseMapLayers{}.resourceInfo.layers{}.subLayerIds,defaultBasemap.baseMapLayers{}.resourceInfo.layers{}.minScale,defaultBasemap.baseMapLayers{}.resourceInfo.layers{}.maxScale,defaultBasemap.baseMapLayers{}.resourceInfo.spatialReference.wkid,defaultBasemap.baseMapLayers{}.resourceInfo.spatialReference.latestWkid,defaultBasemap.baseMapLayers{}.resourceInfo.singleFusedMapCache,defaultBasemap.baseMapLayers{}.resourceInfo.tileInfo.rows,defaultBasemap.baseMapLayers{}.resourceInfo.tileInfo.cols,defaultBasemap.baseMapLayers{}.resourceInfo.tileInfo.dpi,defaultBasemap.baseMapLayers{}.resourceInfo.tileInfo.format,defaultBasemap.baseMapLayers{}.resourceInfo.tileInfo.compressionQuality,defaultBasemap.baseMapLayers{}.resourceInfo.tileInfo.origin.x,defaultBasemap.baseMapLayers{}.resourceInfo.tileInfo.origin.y,defaultBasemap.baseMapLayers{}.resourceInfo.tileInfo.spatialReference.wkid,defaultBasemap.baseMapLayers{}.resourceInfo.tileInfo.spatialReference.latestWkid,defaultBasemap.baseMapLayers{}.resourceInfo.tileInfo.lods{}.level,defaultBasemap.baseMapLayers{}.resourceInfo.tileInfo.lods{}.resolution,defaultBasemap.baseMapLayers{}.resourceInfo.tileInfo.lods{}.scale,defaultBasemap.baseMapLayers{}.resourceInfo.initialExtent.xmin,defaultBasemap.baseMapLayers{}.resourceInfo.initialExtent.ymin,defaultBasemap.baseMapLayers{}.resourceInfo.initialExtent.xmax,defaultBasemap.baseMapLayers{}.resourceInfo.initialExtent.ymax,defaultBasemap.baseMapLayers{}.resourceInfo.initialExtent.spatialReference.wkid,defaultBasemap.baseMapLayers{}.resourceInfo.initialExtent.spatialReference.latestWkid,defaultBasemap.baseMapLayers{}.resourceInfo.fullExtent.xmin,defaultBasemap.baseMapLayers{}.resourceInfo.fullExtent.ymin,defaultBasemap.baseMapLayers{}.resourceInfo.fullExtent.xmax,defaultBasemap.baseMapLayers{}.resourceInfo.fullExtent.ymax,defaultBasemap.baseMapLayers{}.resourceInfo.fullExtent.spatialReference.wkid,defaultBasemap.baseMapLayers{}.resourceInfo.fullExtent.spatialReference.latestWkid,defaultBasemap.baseMapLayers{}.resourceInfo.minScale,defaultBasemap.baseMapLayers{}.resourceInfo.maxScale,defaultBasemap.baseMapLayers{}.resourceInfo.units,defaultBasemap.baseMapLayers{}.resourceInfo.supportedImageFormatTypes,defaultBasemap.baseMapLayers{}.resourceInfo.capabilities,defaultBasemap.baseMapLayers{}.resourceInfo.supportedQueryFormats,defaultBasemap.baseMapLayers{}.resourceInfo.exportTilesAllowed,defaultBasemap.baseMapLayers{}.resourceInfo.maxRecordCount,defaultBasemap.baseMapLayers{}.resourceInfo.maxImageHeight,defaultBasemap.baseMapLayers{}.resourceInfo.maxImageWidth,defaultBasemap.baseMapLayers{}.resourceInfo.supportedExtensions,defaultBasemap.title,defaultDevBasemap.baseMapLayers{}.url,defaultDevBasemap.baseMapLayers{}.id,defaultDevBasemap.baseMapLayers{}.type,defaultDevBasemap.baseMapLayers{}.layerType,defaultDevBasemap.baseMapLayers{}.title,defaultDevBasemap.baseMapLayers{}.styleUrl,defaultDevBasemap.baseMapLayers{}.visibility,defaultDevBasemap.baseMapLayers{}.opacity,defaultDevBasemap.title,defaultExtent.xmin,defaultExtent.ymin,defaultExtent.xmax,defaultExtent.ymax,defaultExtent.spatialReference.wkid,defaultUserCreditAssignment,defaultVectorBasemap.baseMapLayers{}.url,defaultVectorBasemap.baseMapLayers{}.id,defaultVectorBasemap.baseMapLayers{}.type,defaultVectorBasemap.baseMapLayers{}.layerType,defaultVectorBasemap.baseMapLayers{}.title,defaultVectorBasemap.baseMapLayers{}.styleUrl,defaultVectorBasemap.baseMapLayers{}.visibility,defaultVectorBasemap.baseMapLayers{}.opacity,defaultVectorBasemap.title,description,devBasemapGalleryGroupQuery,eueiEnabled,featuredGroups{}.owner,featuredGroups{}.title,featuredItemsGroupQuery,galleryTemplatesGroupQuery,hasCategorySchema,helpBase,helperServices.asyncClosestFacility.url,helperServices.asyncClosestFacility.defaultTravelMode,helperServices.asyncLocationAllocation.url,helperServices.asyncLocationAllocation.defaultTravelMode,helperServices.asyncODCostMatrix.url,helperServices.asyncODCostMatrix.defaultTravelMode,helperServices.asyncRoute.url,helperServices.asyncRoute.defaultTravelMode,helperServices.asyncServiceArea.url,helperServices.asyncServiceArea.defaultTravelMode,helperServices.asyncVRP.url,helperServices.asyncVRP.defaultTravelMode,helperServices.closestFacility.url,helperServices.closestFacility.defaultTravelMode,helperServices.defaultElevationLayers{}.url,helperServices.defaultElevationLayers{}.id,helperServices.defaultElevationLayers{}.layerType,helperServices.elevation.url,helperServices.elevationSync.url,helperServices.geocode{}.url,helperServices.geocode{}.northLat,helperServices.geocode{}.southLat,helperServices.geocode{}.eastLon,helperServices.geocode{}.westLon,helperServices.geocode{}.name,helperServices.geocode{}.batch,helperServices.geocode{}.placefinding,helperServices.geocode{}.suggest,helperServices.geometry.url,helperServices.hydrology.url,helperServices.odCostMatrix.url,helperServices.odCostMatrix.defaultTravelMode,helperServices.orthomappingElevation.url,helperServices.packaging.url,helperServices.packaging.maxMapAreaItemsLimit,helperServices.packaging.exportTilesMap{}.source,helperServices.packaging.exportTilesMap{}.export,helperServices.printTask.url,helperServices.route.url,helperServices.route.defaultTravelMode,helperServices.routingUtilities.url,helperServices.serviceArea.url,helperServices.serviceArea.defaultTravelMode,helperServices.syncVRP.url,helperServices.syncVRP.defaultTravelMode,helperServices.traffic.url,helperServices.trafficData.url,helperServices.analysis.url,helperServices.geoenrichment.url,helperServices.asyncGeocode.url,helperServices.creditEstimation.url,helperServices.rasterAnalytics.url,helperServices.rasterUtilities.url,helperServices.geoanalytics.url,helperServices.datastoreManagement.url,homePageFeaturedContent,homePageFeaturedContentCount,id,isPortal,isVerified,layerTemplatesGroupQuery,livingAtlasGroupQuery,maxTokenExpirationMinutes,metadataEditable,modified,name,notificationsEnabled,portalHostname,portalMode,portalName,portalProperties.mapViewer,portalProperties.mapViewerSwitchDate,portalThumbnail,rasterFunctionTemplatesGroupQuery,region,rotatorPanels,staticImagesUrl,storageQuota,storageUsage,stylesGroupQuery,supportsHostedServices,symbolSetsGroupQuery,templatesGroupQuery,thumbnail,updateUserProfileDisabled,urlKey,useStandardizedQuery,useVectorBasemaps,vectorBasemapGalleryGroupQuery,subscriptionInfo.id,subscriptionInfo.type,subscriptionInfo.state,subscriptionInfo.expDate,subscriptionInfo.userLicenseTypes.creatorUT,subscriptionInfo.userLicenseTypes.viewerUT,subscriptionInfo.maxUsersPerLevel.1,subscriptionInfo.maxUsersPerLevel.2,subscriptionInfo.maxUsers,subscriptionInfo.availableCredits,subscriptionInfo.collaborationSettings.level,subscriptionInfo.collaborationSettings.maxItemSizeInMB,subscriptionInfo.collaborationSettings.maxReplicationPackageSizeInMB,ipCntryCode,httpPort,httpsPort,supportsOAuth,currentVersion,mfaEnabled,contacts{},user.username,user.udn,user.id,user.fullName,user.firstName,user.lastName,user.preferredView,user.description,user.email,user.userType,user.idpUsername,user.favGroupId,user.lastLogin,user.mfaEnabled,user.storageUsage,user.storageQuota,user.orgId,user.role,user.privileges{},user.level,user.userLicenseTypeId,user.disabled,user.culture,user.cultureFormat,user.region,user.units,user.thumbnail,user.access,user.created,user.modified,user.provider,appInfo.appId,appInfo.itemId,appInfo.appOwner,appInfo.orgId,appInfo.appTitle,appInfo.privileges{}"
    ATTR_ACCUM_MODE = Merge Initiator and Result
    ATTR_CONFLICT_RES = Use Result
    ATTR_IGNORE_NULLS = No
    COMBINE_GEOM = Use Result
    DATASET = https://www.arcgis.com/sharing/rest/portals/self/properties?f=json&token=@Value(Token)
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    ORDER_RESULTS = No
    OUTPUT_FEATURES_DISPLAY = Schema and Data Features
    JSONFeature -> AttributeManager_5
    JSONFeature -> AttributeManager_4

Bookmark: Parse REST Service List - To get List of all services
AttributeManager_5
    ATTR_TABLE:
      SET_TO URL (varchar(200)) = https://$(RESTServiceHive).arcgis.com/@Value(id)/arcgis/rest/services?f=json&token=@Value(Token)
      REMOVE _creation_instance (uint64)
      REMOVE 2DStylesGroupQuery (buffer)
      REMOVE access (buffer)
      REMOVE allSSL (logical)
      REMOVE analysisLayersGroupQuery (buffer)
      REMOVE availableCredits (real64)
      REMOVE basemapGalleryGroupQuery (buffer)
      REMOVE canListApps (logical)
      REMOVE canListConsultingServices (logical)
      REMOVE canListData (logical)
      REMOVE canListPreProvisionedItems (logical)
      REMOVE canListSolutions (logical)
      REMOVE canProvisionDirectPurchase (logical)
      REMOVE canSearchPublic (logical)
      REMOVE canSetCustomBuyLink (logical)
      REMOVE canSetQuestionnaire (logical)
      REMOVE canSharePublic (logical)
      REMOVE canSignInArcGIS (logical)
      REMOVE canSignInIDP (logical)
      REMOVE canSignInOIDC (logical)
      REMOVE canSignInSocial (logical)
      REMOVE colorSetsGroupQuery (buffer)
      REMOVE commentsEnabled (logical)
      REMOVE contentCategorySetsGroupQuery (buffer)
      REMOVE created (int64)
      REMOVE culture (buffer)
      REMOVE cultureFormat (buffer)
      REMOVE customBaseUrl (buffer)
      REMOVE databaseQuota (int64)
      REMOVE databaseUsage (int64)
      REMOVE defaultBasemap.baseMapLayers{}.url (buffer)
      REMOVE defaultBasemap.baseMapLayers{}.layerType (buffer)
      REMOVE defaultBasemap.baseMapLayers{}.resourceInfo.currentVersion (real64)
      REMOVE defaultBasemap.baseMapLayers{}.resourceInfo.mapName (buffer)
      REMOVE defaultBasemap.baseMapLayers{}.resourceInfo.supportsDynamicLayers (logical)
      REMOVE defaultBasemap.baseMapLayers{}.resourceInfo.layers{}.id (int64)
      REMOVE defaultBasemap.baseMapLayers{}.resourceInfo.layers{}.name (buffer)
      REMOVE defaultBasemap.baseMapLayers{}.resourceInfo.layers{}.parentLayerId (int64)
      REMOVE defaultBasemap.baseMapLayers{}.resourceInfo.layers{}.defaultVisibility (logical)
      REMOVE defaultBasemap.baseMapLayers{}.resourceInfo.layers{}.subLayerIds (buffer)
      REMOVE defaultBasemap.baseMapLayers{}.resourceInfo.layers{}.minScale (int64)
      REMOVE defaultBasemap.baseMapLayers{}.resourceInfo.layers{}.maxScale (int64)
      REMOVE defaultBasemap.baseMapLayers{}.resourceInfo.spatialReference.wkid (int64)
      REMOVE defaultBasemap.baseMapLayers{}.resourceInfo.spatialReference.latestWkid (int64)
      REMOVE defaultBasemap.baseMapLayers{}.resourceInfo.singleFusedMapCache (logical)
      REMOVE defaultBasemap.baseMapLayers{}.resourceInfo.tileInfo.rows (int64)
      REMOVE defaultBasemap.baseMapLayers{}.resourceInfo.tileInfo.cols (int64)
      REMOVE defaultBasemap.baseMapLayers{}.resourceInfo.tileInfo.dpi (int64)
      REMOVE defaultBasemap.baseMapLayers{}.resourceInfo.tileInfo.format (buffer)
      REMOVE defaultBasemap.baseMapLayers{}.resourceInfo.tileInfo.compressionQuality (int64)
      REMOVE defaultBasemap.baseMapLayers{}.resourceInfo.tileInfo.origin.x (real64)
      REMOVE defaultBasemap.baseMapLayers{}.resourceInfo.tileInfo.origin.y (real64)
      REMOVE defaultBasemap.baseMapLayers{}.resourceInfo.tileInfo.spatialReference.wkid (int64)
      REMOVE defaultBasemap.baseMapLayers{}.resourceInfo.tileInfo.spatialReference.latestWkid (int64)
      REMOVE defaultBasemap.baseMapLayers{}.resourceInfo.tileInfo.lods{}.level (int64)
      REMOVE defaultBasemap.baseMapLayers{}.resourceInfo.tileInfo.lods{}.resolution (real64)
      REMOVE defaultBasemap.baseMapLayers{}.resourceInfo.tileInfo.lods{}.scale (real64)
      REMOVE defaultBasemap.baseMapLayers{}.resourceInfo.initialExtent.xmin (real64)
      REMOVE defaultBasemap.baseMapLayers{}.resourceInfo.initialExtent.ymin (real64)
      REMOVE defaultBasemap.baseMapLayers{}.resourceInfo.initialExtent.xmax (real64)
      REMOVE defaultBasemap.baseMapLayers{}.resourceInfo.initialExtent.ymax (real64)
      REMOVE defaultBasemap.baseMapLayers{}.resourceInfo.initialExtent.spatialReference.wkid (int64)
      REMOVE defaultBasemap.baseMapLayers{}.resourceInfo.initialExtent.spatialReference.latestWkid (int64)
      REMOVE defaultBasemap.baseMapLayers{}.resourceInfo.fullExtent.xmin (real64)
      REMOVE defaultBasemap.baseMapLayers{}.resourceInfo.fullExtent.ymin (real64)
      REMOVE defaultBasemap.baseMapLayers{}.resourceInfo.fullExtent.xmax (real64)
      REMOVE defaultBasemap.baseMapLayers{}.resourceInfo.fullExtent.ymax (real64)
      REMOVE defaultBasemap.baseMapLayers{}.resourceInfo.fullExtent.spatialReference.wkid (int64)
      REMOVE defaultBasemap.baseMapLayers{}.resourceInfo.fullExtent.spatialReference.latestWkid (int64)
      REMOVE defaultBasemap.baseMapLayers{}.resourceInfo.minScale (real64)
      REMOVE defaultBasemap.baseMapLayers{}.resourceInfo.maxScale (real64)
      REMOVE defaultBasemap.baseMapLayers{}.resourceInfo.units (buffer)
      REMOVE defaultBasemap.baseMapLayers{}.resourceInfo.supportedImageFormatTypes (buffer)
      REMOVE defaultBasemap.baseMapLayers{}.resourceInfo.capabilities (buffer)
      REMOVE defaultBasemap.baseMapLayers{}.resourceInfo.supportedQueryFormats (buffer)
      REMOVE defaultBasemap.baseMapLayers{}.resourceInfo.exportTilesAllowed (logical)
      REMOVE defaultBasemap.baseMapLayers{}.resourceInfo.maxRecordCount (int64)
      REMOVE defaultBasemap.baseMapLayers{}.resourceInfo.maxImageHeight (int64)
      REMOVE defaultBasemap.baseMapLayers{}.resourceInfo.maxImageWidth (int64)
      REMOVE defaultBasemap.baseMapLayers{}.resourceInfo.supportedExtensions (buffer)
      REMOVE defaultBasemap.title (buffer)
      REMOVE defaultDevBasemap.baseMapLayers{}.url (buffer)
      REMOVE defaultDevBasemap.baseMapLayers{}.id (buffer)
      REMOVE defaultDevBasemap.baseMapLayers{}.type (buffer)
      REMOVE defaultDevBasemap.baseMapLayers{}.layerType (buffer)
      REMOVE defaultDevBasemap.baseMapLayers{}.title (buffer)
      REMOVE defaultDevBasemap.baseMapLayers{}.styleUrl (buffer)
      REMOVE defaultDevBasemap.baseMapLayers{}.visibility (logical)
      REMOVE defaultDevBasemap.baseMapLayers{}.opacity (int64)
      REMOVE defaultDevBasemap.title (buffer)
      REMOVE defaultExtent.xmin (int64)
      REMOVE defaultExtent.ymin (int64)
      REMOVE defaultExtent.xmax (int64)
      REMOVE defaultExtent.ymax (int64)
      REMOVE defaultExtent.spatialReference.wkid (int64)
      REMOVE defaultUserCreditAssignment (int64)
      REMOVE defaultVectorBasemap.baseMapLayers{}.url (buffer)
      REMOVE defaultVectorBasemap.baseMapLayers{}.id (buffer)
      REMOVE defaultVectorBasemap.baseMapLayers{}.type (buffer)
      REMOVE defaultVectorBasemap.baseMapLayers{}.layerType (buffer)
      REMOVE defaultVectorBasemap.baseMapLayers{}.title (buffer)
      REMOVE defaultVectorBasemap.baseMapLayers{}.styleUrl (buffer)
      REMOVE defaultVectorBasemap.baseMapLayers{}.visibility (logical)
      REMOVE defaultVectorBasemap.baseMapLayers{}.opacity (int64)
      REMOVE defaultVectorBasemap.title (buffer)
      REMOVE description (buffer)
      REMOVE devBasemapGalleryGroupQuery (buffer)
      REMOVE eueiEnabled (logical)
      REMOVE featuredGroups{}.owner (buffer)
      REMOVE featuredGroups{}.title (buffer)
      REMOVE featuredItemsGroupQuery (buffer)
      REMOVE galleryTemplatesGroupQuery (buffer)
      REMOVE hasCategorySchema (logical)
      REMOVE helpBase (buffer)
      REMOVE helperServices.asyncClosestFacility.url (buffer)
      REMOVE helperServices.asyncClosestFacility.defaultTravelMode (buffer)
      REMOVE helperServices.asyncLocationAllocation.url (buffer)
      REMOVE helperServices.asyncLocationAllocation.defaultTravelMode (buffer)
      REMOVE helperServices.asyncODCostMatrix.url (buffer)
      REMOVE helperServices.asyncODCostMatrix.defaultTravelMode (buffer)
      REMOVE helperServices.asyncRoute.url (buffer)
      REMOVE helperServices.asyncRoute.defaultTravelMode (buffer)
      REMOVE helperServices.asyncServiceArea.url (buffer)
      REMOVE helperServices.asyncServiceArea.defaultTravelMode (buffer)
      REMOVE helperServices.asyncVRP.url (buffer)
      REMOVE helperServices.asyncVRP.defaultTravelMode (buffer)
      REMOVE helperServices.closestFacility.url (buffer)
      REMOVE helperServices.closestFacility.defaultTravelMode (buffer)
      REMOVE helperServices.defaultElevationLayers{}.url (buffer)
      REMOVE helperServices.defaultElevationLayers{}.id (buffer)
      REMOVE helperServices.defaultElevationLayers{}.layerType (buffer)
      REMOVE helperServices.elevation.url (buffer)
      REMOVE helperServices.elevationSync.url (buffer)
      REMOVE helperServices.geocode{}.url (buffer)
      REMOVE helperServices.geocode{}.northLat (buffer)
      REMOVE helperServices.geocode{}.southLat (buffer)
      REMOVE helperServices.geocode{}.eastLon (buffer)
      REMOVE helperServices.geocode{}.westLon (buffer)
      REMOVE helperServices.geocode{}.name (buffer)
      REMOVE helperServices.geocode{}.batch (logical)
      REMOVE helperServices.geocode{}.placefinding (logical)
      REMOVE helperServices.geocode{}.suggest (logical)
      REMOVE helperServices.geometry.url (buffer)
      REMOVE helperServices.hydrology.url (buffer)
      REMOVE helperServices.odCostMatrix.url (buffer)
      REMOVE helperServices.odCostMatrix.defaultTravelMode (buffer)
      REMOVE helperServices.orthomappingElevation.url (buffer)
      REMOVE helperServices.packaging.url (buffer)
      REMOVE helperServices.packaging.maxMapAreaItemsLimit (int64)
      REMOVE helperServices.packaging.exportTilesMap{}.source (buffer)
      REMOVE helperServices.packaging.exportTilesMap{}.export (buffer)
      REMOVE helperServices.printTask.url (buffer)
      REMOVE helperServices.route.url (buffer)
      REMOVE helperServices.route.defaultTravelMode (buffer)
      REMOVE helperServices.routingUtilities.url (buffer)
      REMOVE helperServices.serviceArea.url (buffer)
      REMOVE helperServices.serviceArea.defaultTravelMode (buffer)
      REMOVE helperServices.syncVRP.url (buffer)
      REMOVE helperServices.syncVRP.defaultTravelMode (buffer)
      REMOVE helperServices.traffic.url (buffer)
      REMOVE helperServices.trafficData.url (buffer)
      REMOVE helperServices.analysis.url (buffer)
      REMOVE helperServices.geoenrichment.url (buffer)
      REMOVE helperServices.asyncGeocode.url (buffer)
      REMOVE helperServices.creditEstimation.url (buffer)
      REMOVE helperServices.rasterAnalytics.url (buffer)
      REMOVE helperServices.rasterUtilities.url (buffer)
      REMOVE helperServices.geoanalytics.url (buffer)
      REMOVE helperServices.datastoreManagement.url (buffer)
      REMOVE homePageFeaturedContent (buffer)
      REMOVE homePageFeaturedContentCount (int64)
      REMOVE isPortal (logical)
      REMOVE isVerified (logical)
      REMOVE layerTemplatesGroupQuery (buffer)
      REMOVE livingAtlasGroupQuery (buffer)
      REMOVE maxTokenExpirationMinutes (int64)
      REMOVE metadataEditable (logical)
      REMOVE modified (int64)
      REMOVE name (buffer)
      REMOVE notificationsEnabled (logical)
      REMOVE portalHostname (buffer)
      REMOVE portalMode (buffer)
      REMOVE portalName (buffer)
      REMOVE portalProperties.mapViewer (buffer)
      REMOVE portalProperties.mapViewerSwitchDate (int64)
      REMOVE portalThumbnail (buffer)
      REMOVE rasterFunctionTemplatesGroupQuery (buffer)
      REMOVE region (buffer)
      REMOVE rotatorPanels (buffer)
      REMOVE staticImagesUrl (buffer)
      REMOVE storageQuota (int64)
      REMOVE storageUsage (int64)
      REMOVE stylesGroupQuery (buffer)
      REMOVE supportsHostedServices (logical)
      REMOVE symbolSetsGroupQuery (buffer)
      REMOVE templatesGroupQuery (buffer)
      REMOVE thumbnail (buffer)
      REMOVE updateUserProfileDisabled (logical)
      REMOVE useStandardizedQuery (logical)
      REMOVE useVectorBasemaps (logical)
      REMOVE vectorBasemapGalleryGroupQuery (buffer)
      REMOVE subscriptionInfo.id (buffer)
      REMOVE subscriptionInfo.type (buffer)
      REMOVE subscriptionInfo.state (buffer)
      REMOVE subscriptionInfo.expDate (int64)
      REMOVE subscriptionInfo.userLicenseTypes.creatorUT (int64)
      REMOVE subscriptionInfo.userLicenseTypes.viewerUT (int64)
      REMOVE subscriptionInfo.maxUsersPerLevel.1 (int64)
      REMOVE subscriptionInfo.maxUsersPerLevel.2 (int64)
      REMOVE subscriptionInfo.maxUsers (int64)
      REMOVE subscriptionInfo.availableCredits (real64)
      REMOVE subscriptionInfo.collaborationSettings.level (buffer)
      REMOVE subscriptionInfo.collaborationSettings.maxItemSizeInMB (int64)
      REMOVE subscriptionInfo.collaborationSettings.maxReplicationPackageSizeInMB (int64)
      REMOVE ipCntryCode (buffer)
      REMOVE httpPort (int64)
      REMOVE httpsPort (int64)
      REMOVE supportsOAuth (logical)
      REMOVE currentVersion (buffer)
      REMOVE mfaEnabled (logical)
      REMOVE contacts{} (buffer)
      REMOVE user.username (buffer)
      REMOVE user.udn (buffer)
      REMOVE user.id (buffer)
      REMOVE user.fullName (buffer)
      REMOVE user.firstName (buffer)
      REMOVE user.lastName (buffer)
      REMOVE user.preferredView (buffer)
      REMOVE user.description (buffer)
      REMOVE user.email (buffer)
      REMOVE user.userType (buffer)
      REMOVE user.idpUsername (buffer)
      REMOVE user.favGroupId (buffer)
      REMOVE user.lastLogin (int64)
      REMOVE user.mfaEnabled (logical)
      REMOVE user.storageUsage (int64)
      REMOVE user.storageQuota (int64)
      REMOVE user.orgId (buffer)
      REMOVE user.role (buffer)
      REMOVE user.privileges{} (buffer)
      REMOVE user.level (buffer)
      REMOVE user.userLicenseTypeId (buffer)
      REMOVE user.disabled (logical)
      REMOVE user.culture (buffer)
      REMOVE user.cultureFormat (buffer)
      REMOVE user.region (buffer)
      REMOVE user.units (buffer)
      REMOVE user.thumbnail (buffer)
      REMOVE user.access (buffer)
      REMOVE user.created (int64)
      REMOVE user.modified (int64)
      REMOVE user.provider (buffer)
      REMOVE appInfo.appId (buffer)
      REMOVE appInfo.itemId (buffer)
      REMOVE appInfo.appOwner (buffer)
      REMOVE appInfo.orgId (buffer)
      REMOVE appInfo.appTitle (buffer)
      REMOVE appInfo.privileges{} (buffer)
    -> ParseRESTServiceList [INITIATOR]
Note: Read REST API to get all the public services!
ParseRESTServiceList: FeatureReader
    ATTRIBUTES = JSONFeature,"currentVersion,services{}.name,services{}.type,services{}.url"
    ATTR_ACCUM_MODE = Merge Initiator and Result
    ATTR_CONFLICT_RES = Use Result
    ATTR_IGNORE_NULLS = No
    COMBINE_GEOM = Use Result
    DATASET = @Value(URL)
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    ORDER_RESULTS = No
    OUTPUT_FEATURES_DISPLAY = Schema and Data Features
    JSONFeature -> ListExploder_3
ListExploder_3
    ATTR_ACCUM_MODE = Merge List Attributes
    ATTR_CONFLICT_RES = Use List Attribute Values
    INDEX_ATTR = _element_index
    LIST_ATTR = services{}
    ELEMENTS -> AttributeManager_2

Bookmark: Parse Rest Service Usage
Note: Max is 7 days: 604800000 / 1 Day: 86400000
AttributeManager_2
    ATTR_TABLE:
      REMOVE URL (varchar(200))
      SET_TO Service_Name (buffer) = @Value(name)
      SET_TO Name (buffer) = @Value(name)
      SET_TO Type (varchar(200)) = Service
      SET_TO endTime (varchar(200)) = FME_CONDITIONAL:DEFAULT_VALUE'$(EPOCH_End)'BOOL_OP;OR;COMPOSITE_TEST;<Unused>;TEST $(EPOCH_End) NOT_ATTRIBUTE_HAS_A_VALUE _FME_BLANK_STRING_'@Left(@DateTimeFormat(@DateTimeNow(utc),%s),10)000'FME_NUM_CONDITIONS2___
      SET_TO startTime (varchar(200)) = FME_CONDITIONAL:DEFAULT_VALUE'@Evaluate(@Value(endTime)-86400000)'BOOL_OP;OR;COMPOSITE_TEST;1;TEST $(EPOCH_Start) ATTRIBUTE_HAS_A_VALUE _FME_BLANK_STRING_'$(EPOCH_Start)'FME_NUM_CONDITIONS2___
      SET_TO URL (varchar(200)) = FME_CONDITIONAL:DEFAULT_VALUE'_FME_NO_OP_'BOOL_OP;OR;COMPOSITE_TEST;<Unused>;TEST @Value(Type) = Service'https://@Value(urlKey).maps.arcgis.com/sharing/rest/portals/@Value(id)/usage?f=json&startTime=@Value(startTime)&endTime=@Value(endTime)&period=1h&vars=num&groupby=name&etype=svcusg&name=@Value(Service_Name)&stype=features&token=@Value(Token)'FME_NUM_CONDITIONS2___
      REMOVE currentVersion (real64)
      REMOVE name (buffer)
      REMOVE type (buffer)
      REMOVE url (buffer)
      REMOVE _element_index (uint32)
    -> GetRESTServiceUsage [INITIATOR]
GetRESTServiceUsage: FeatureReader
    ATTRIBUTES = JSONFeature,"startTime,endTime,period,data{}.etype,data{}.name,data{}.stype,data{}.num{}.array{},fme_geometry{0}"
    ATTR_ACCUM_MODE = Merge Initiator and Result
    ATTR_CONFLICT_RES = Use Result
    ATTR_IGNORE_NULLS = No
    COMBINE_GEOM = Use Result
    DATASET = @Value(URL)
    FEATURETYPES = JSONFeature
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    ORDER_RESULTS = No
    OUTPUT_FEATURES_DISPLAY = Schema and Data Features
    JSONFeature -> AttributeManager_3
AttributeManager_3
    ATTR_TABLE:
      REMOVE endTime (varchar(200))
      REMOVE startTime (varchar(200))
      REMOVE URL (varchar(200))
      REMOVE fme_geometry{0} (varchar(200))
      REMOVE fme_geometry{} (varchar(200))
    -> ListExploder
ListExploder
    ATTR_ACCUM_MODE = Merge List Attributes
    ATTR_CONFLICT_RES = Use List Attribute Values
    INDEX_ATTR = _element_index
    LIST_ATTR = data{}
    ELEMENTS -> ListExploder_2
    <REJECTED> -> No_Data
No_Data: Logger
    LOG_FEATURE = LOG_ONLY
    MAXCOORDS = 20
    MAXFEATS = 200
    MESSAGE:
      Name: @Value(Name) (@Value(id))
      Type: @Value(Type)
    SEVERITY = INFO
ListExploder_2
    ATTR_ACCUM_MODE = Merge List Attributes
    ATTR_CONFLICT_RES = Use List Attribute Values
    INDEX_ATTR = _element_index
    LIST_ATTR = num{}
    ELEMENTS -> AttributeExposer
AttributeExposer
    ATTR_LIST = array{0},array{1}
    -> AttributeManager
AttributeManager
    ATTR_TABLE:
      REMOVE name (varchar(200))
      RENAME_SET_VALUE period > timeperiod (varchar(200))
      RENAME_SET_VALUE Name > name (buffer)
      RENAME_SET_VALUE Type > type (varchar(200))
      RENAME_SET_VALUE array{0} > utchour (varchar(200))
      RENAME_SET_VALUE array{1} > count (varchar(200))
      REMOVE etype (varchar(200))
      REMOVE stype (varchar(200))
      REMOVE _element_index (uint32)
      REMOVE array{} (varchar(200))
      REMOVE Service_Name (buffer)
      SET_TO utchour (varchar(200)) = @DateTimeFormat(@DateTimeParse(@Left(@Value(utchour),10),%Es),%Y%m%d%H%M%S)
      REMOVE Token (varchar(200))
      REMOVE id (buffer)
      REMOVE urlKey (buffer)
    -> REST_Services (writer FFS_1)
REST_Services (writer FFS_1)
    attributes: timeperiod varchar(200), name buffer, type varchar(200), count varchar(200), utchour varchar(200)

Bookmark: Parse Data Store Performance
Note: Remember that this is a SHARED data store / (unless the org has bought a premium data store)
AttributeManager_4
    ATTR_TABLE:
      SET_TO URL (varchar(200)) = https://datastoremanagement.arcgis.com/@Value(id)/datastores/featureDataStore?metric=db_avg_cpu&ago=7&agoUnit=d&binSize=1&binUnit=h&binAggregation=max&f=json&token=@Value(Token)
      REMOVE _creation_instance (uint64)
      REMOVE 2DStylesGroupQuery (buffer)
      REMOVE access (buffer)
      REMOVE allSSL (logical)
      REMOVE analysisLayersGroupQuery (buffer)
      REMOVE availableCredits (real64)
      REMOVE basemapGalleryGroupQuery (buffer)
      REMOVE canListApps (logical)
      REMOVE canListConsultingServices (logical)
      REMOVE canListData (logical)
      REMOVE canListPreProvisionedItems (logical)
      REMOVE canListSolutions (logical)
      REMOVE canProvisionDirectPurchase (logical)
      REMOVE canSearchPublic (logical)
      REMOVE canSetCustomBuyLink (logical)
      REMOVE canSetQuestionnaire (logical)
      REMOVE canSharePublic (logical)
      REMOVE canSignInArcGIS (logical)
      REMOVE canSignInIDP (logical)
      REMOVE canSignInOIDC (logical)
      REMOVE canSignInSocial (logical)
      REMOVE colorSetsGroupQuery (buffer)
      REMOVE commentsEnabled (logical)
      REMOVE contentCategorySetsGroupQuery (buffer)
      REMOVE created (int64)
      REMOVE culture (buffer)
      REMOVE cultureFormat (buffer)
      REMOVE customBaseUrl (buffer)
      REMOVE databaseQuota (int64)
      REMOVE databaseUsage (int64)
      REMOVE defaultBasemap.baseMapLayers{}.url (buffer)
      REMOVE defaultBasemap.baseMapLayers{}.layerType (buffer)
      REMOVE defaultBasemap.baseMapLayers{}.resourceInfo.currentVersion (real64)
      REMOVE defaultBasemap.baseMapLayers{}.resourceInfo.mapName (buffer)
      REMOVE defaultBasemap.baseMapLayers{}.resourceInfo.supportsDynamicLayers (logical)
      REMOVE defaultBasemap.baseMapLayers{}.resourceInfo.layers{}.id (int64)
      REMOVE defaultBasemap.baseMapLayers{}.resourceInfo.layers{}.name (buffer)
      REMOVE defaultBasemap.baseMapLayers{}.resourceInfo.layers{}.parentLayerId (int64)
      REMOVE defaultBasemap.baseMapLayers{}.resourceInfo.layers{}.defaultVisibility (logical)
      REMOVE defaultBasemap.baseMapLayers{}.resourceInfo.layers{}.subLayerIds (buffer)
      REMOVE defaultBasemap.baseMapLayers{}.resourceInfo.layers{}.minScale (int64)
      REMOVE defaultBasemap.baseMapLayers{}.resourceInfo.layers{}.maxScale (int64)
      REMOVE defaultBasemap.baseMapLayers{}.resourceInfo.spatialReference.wkid (int64)
      REMOVE defaultBasemap.baseMapLayers{}.resourceInfo.spatialReference.latestWkid (int64)
      REMOVE defaultBasemap.baseMapLayers{}.resourceInfo.singleFusedMapCache (logical)
      REMOVE defaultBasemap.baseMapLayers{}.resourceInfo.tileInfo.rows (int64)
      REMOVE defaultBasemap.baseMapLayers{}.resourceInfo.tileInfo.cols (int64)
      REMOVE defaultBasemap.baseMapLayers{}.resourceInfo.tileInfo.dpi (int64)
      REMOVE defaultBasemap.baseMapLayers{}.resourceInfo.tileInfo.format (buffer)
      REMOVE defaultBasemap.baseMapLayers{}.resourceInfo.tileInfo.compressionQuality (int64)
      REMOVE defaultBasemap.baseMapLayers{}.resourceInfo.tileInfo.origin.x (real64)
      REMOVE defaultBasemap.baseMapLayers{}.resourceInfo.tileInfo.origin.y (real64)
      REMOVE defaultBasemap.baseMapLayers{}.resourceInfo.tileInfo.spatialReference.wkid (int64)
      REMOVE defaultBasemap.baseMapLayers{}.resourceInfo.tileInfo.spatialReference.latestWkid (int64)
      REMOVE defaultBasemap.baseMapLayers{}.resourceInfo.tileInfo.lods{}.level (int64)
      REMOVE defaultBasemap.baseMapLayers{}.resourceInfo.tileInfo.lods{}.resolution (real64)
      REMOVE defaultBasemap.baseMapLayers{}.resourceInfo.tileInfo.lods{}.scale (real64)
      REMOVE defaultBasemap.baseMapLayers{}.resourceInfo.initialExtent.xmin (real64)
      REMOVE defaultBasemap.baseMapLayers{}.resourceInfo.initialExtent.ymin (real64)
      REMOVE defaultBasemap.baseMapLayers{}.resourceInfo.initialExtent.xmax (real64)
      REMOVE defaultBasemap.baseMapLayers{}.resourceInfo.initialExtent.ymax (real64)
      REMOVE defaultBasemap.baseMapLayers{}.resourceInfo.initialExtent.spatialReference.wkid (int64)
      REMOVE defaultBasemap.baseMapLayers{}.resourceInfo.initialExtent.spatialReference.latestWkid (int64)
      REMOVE defaultBasemap.baseMapLayers{}.resourceInfo.fullExtent.xmin (real64)
      REMOVE defaultBasemap.baseMapLayers{}.resourceInfo.fullExtent.ymin (real64)
      REMOVE defaultBasemap.baseMapLayers{}.resourceInfo.fullExtent.xmax (real64)
      REMOVE defaultBasemap.baseMapLayers{}.resourceInfo.fullExtent.ymax (real64)
      REMOVE defaultBasemap.baseMapLayers{}.resourceInfo.fullExtent.spatialReference.wkid (int64)
      REMOVE defaultBasemap.baseMapLayers{}.resourceInfo.fullExtent.spatialReference.latestWkid (int64)
      REMOVE defaultBasemap.baseMapLayers{}.resourceInfo.minScale (real64)
      REMOVE defaultBasemap.baseMapLayers{}.resourceInfo.maxScale (real64)
      REMOVE defaultBasemap.baseMapLayers{}.resourceInfo.units (buffer)
      REMOVE defaultBasemap.baseMapLayers{}.resourceInfo.supportedImageFormatTypes (buffer)
      REMOVE defaultBasemap.baseMapLayers{}.resourceInfo.capabilities (buffer)
      REMOVE defaultBasemap.baseMapLayers{}.resourceInfo.supportedQueryFormats (buffer)
      REMOVE defaultBasemap.baseMapLayers{}.resourceInfo.exportTilesAllowed (logical)
      REMOVE defaultBasemap.baseMapLayers{}.resourceInfo.maxRecordCount (int64)
      REMOVE defaultBasemap.baseMapLayers{}.resourceInfo.maxImageHeight (int64)
      REMOVE defaultBasemap.baseMapLayers{}.resourceInfo.maxImageWidth (int64)
      REMOVE defaultBasemap.baseMapLayers{}.resourceInfo.supportedExtensions (buffer)
      REMOVE defaultBasemap.title (buffer)
      REMOVE defaultDevBasemap.baseMapLayers{}.url (buffer)
      REMOVE defaultDevBasemap.baseMapLayers{}.id (buffer)
      REMOVE defaultDevBasemap.baseMapLayers{}.type (buffer)
      REMOVE defaultDevBasemap.baseMapLayers{}.layerType (buffer)
      REMOVE defaultDevBasemap.baseMapLayers{}.title (buffer)
      REMOVE defaultDevBasemap.baseMapLayers{}.styleUrl (buffer)
      REMOVE defaultDevBasemap.baseMapLayers{}.visibility (logical)
      REMOVE defaultDevBasemap.baseMapLayers{}.opacity (int64)
      REMOVE defaultDevBasemap.title (buffer)
      REMOVE defaultExtent.xmin (int64)
      REMOVE defaultExtent.ymin (int64)
      REMOVE defaultExtent.xmax (int64)
      REMOVE defaultExtent.ymax (int64)
      REMOVE defaultExtent.spatialReference.wkid (int64)
      REMOVE defaultUserCreditAssignment (int64)
      REMOVE defaultVectorBasemap.baseMapLayers{}.url (buffer)
      REMOVE defaultVectorBasemap.baseMapLayers{}.id (buffer)
      REMOVE defaultVectorBasemap.baseMapLayers{}.type (buffer)
      REMOVE defaultVectorBasemap.baseMapLayers{}.layerType (buffer)
      REMOVE defaultVectorBasemap.baseMapLayers{}.title (buffer)
      REMOVE defaultVectorBasemap.baseMapLayers{}.styleUrl (buffer)
      REMOVE defaultVectorBasemap.baseMapLayers{}.visibility (logical)
      REMOVE defaultVectorBasemap.baseMapLayers{}.opacity (int64)
      REMOVE defaultVectorBasemap.title (buffer)
      REMOVE description (buffer)
      REMOVE devBasemapGalleryGroupQuery (buffer)
      REMOVE eueiEnabled (logical)
      REMOVE featuredGroups{}.owner (buffer)
      REMOVE featuredGroups{}.title (buffer)
      REMOVE featuredItemsGroupQuery (buffer)
      REMOVE galleryTemplatesGroupQuery (buffer)
      REMOVE hasCategorySchema (logical)
      REMOVE helpBase (buffer)
      REMOVE helperServices.asyncClosestFacility.url (buffer)
      REMOVE helperServices.asyncClosestFacility.defaultTravelMode (buffer)
      REMOVE helperServices.asyncLocationAllocation.url (buffer)
      REMOVE helperServices.asyncLocationAllocation.defaultTravelMode (buffer)
      REMOVE helperServices.asyncODCostMatrix.url (buffer)
      REMOVE helperServices.asyncODCostMatrix.defaultTravelMode (buffer)
      REMOVE helperServices.asyncRoute.url (buffer)
      REMOVE helperServices.asyncRoute.defaultTravelMode (buffer)
      REMOVE helperServices.asyncServiceArea.url (buffer)
      REMOVE helperServices.asyncServiceArea.defaultTravelMode (buffer)
      REMOVE helperServices.asyncVRP.url (buffer)
      REMOVE helperServices.asyncVRP.defaultTravelMode (buffer)
      REMOVE helperServices.closestFacility.url (buffer)
      REMOVE helperServices.closestFacility.defaultTravelMode (buffer)
      REMOVE helperServices.defaultElevationLayers{}.url (buffer)
      REMOVE helperServices.defaultElevationLayers{}.id (buffer)
      REMOVE helperServices.defaultElevationLayers{}.layerType (buffer)
      REMOVE helperServices.elevation.url (buffer)
      REMOVE helperServices.elevationSync.url (buffer)
      REMOVE helperServices.geocode{}.url (buffer)
      REMOVE helperServices.geocode{}.northLat (buffer)
      REMOVE helperServices.geocode{}.southLat (buffer)
      REMOVE helperServices.geocode{}.eastLon (buffer)
      REMOVE helperServices.geocode{}.westLon (buffer)
      REMOVE helperServices.geocode{}.name (buffer)
      REMOVE helperServices.geocode{}.batch (logical)
      REMOVE helperServices.geocode{}.placefinding (logical)
      REMOVE helperServices.geocode{}.suggest (logical)
      REMOVE helperServices.geometry.url (buffer)
      REMOVE helperServices.hydrology.url (buffer)
      REMOVE helperServices.odCostMatrix.url (buffer)
      REMOVE helperServices.odCostMatrix.defaultTravelMode (buffer)
      REMOVE helperServices.orthomappingElevation.url (buffer)
      REMOVE helperServices.packaging.url (buffer)
      REMOVE helperServices.packaging.maxMapAreaItemsLimit (int64)
      REMOVE helperServices.packaging.exportTilesMap{}.source (buffer)
      REMOVE helperServices.packaging.exportTilesMap{}.export (buffer)
      REMOVE helperServices.printTask.url (buffer)
      REMOVE helperServices.route.url (buffer)
      REMOVE helperServices.route.defaultTravelMode (buffer)
      REMOVE helperServices.routingUtilities.url (buffer)
      REMOVE helperServices.serviceArea.url (buffer)
      REMOVE helperServices.serviceArea.defaultTravelMode (buffer)
      REMOVE helperServices.syncVRP.url (buffer)
      REMOVE helperServices.syncVRP.defaultTravelMode (buffer)
      REMOVE helperServices.traffic.url (buffer)
      REMOVE helperServices.trafficData.url (buffer)
      REMOVE helperServices.analysis.url (buffer)
      REMOVE helperServices.geoenrichment.url (buffer)
      REMOVE helperServices.asyncGeocode.url (buffer)
      REMOVE helperServices.creditEstimation.url (buffer)
      REMOVE helperServices.rasterAnalytics.url (buffer)
      REMOVE helperServices.rasterUtilities.url (buffer)
      REMOVE helperServices.geoanalytics.url (buffer)
      REMOVE helperServices.datastoreManagement.url (buffer)
      REMOVE homePageFeaturedContent (buffer)
      REMOVE homePageFeaturedContentCount (int64)
      REMOVE isPortal (logical)
      REMOVE isVerified (logical)
      REMOVE layerTemplatesGroupQuery (buffer)
      REMOVE livingAtlasGroupQuery (buffer)
      REMOVE maxTokenExpirationMinutes (int64)
      REMOVE metadataEditable (logical)
      REMOVE modified (int64)
      REMOVE name (buffer)
      REMOVE notificationsEnabled (logical)
      REMOVE portalHostname (buffer)
      REMOVE portalMode (buffer)
      REMOVE portalName (buffer)
      REMOVE portalProperties.mapViewer (buffer)
      REMOVE portalProperties.mapViewerSwitchDate (int64)
      REMOVE portalThumbnail (buffer)
      REMOVE rasterFunctionTemplatesGroupQuery (buffer)
      REMOVE region (buffer)
      REMOVE rotatorPanels (buffer)
      REMOVE staticImagesUrl (buffer)
      REMOVE storageQuota (int64)
      REMOVE storageUsage (int64)
      REMOVE stylesGroupQuery (buffer)
      REMOVE supportsHostedServices (logical)
      REMOVE symbolSetsGroupQuery (buffer)
      REMOVE templatesGroupQuery (buffer)
      REMOVE thumbnail (buffer)
      REMOVE updateUserProfileDisabled (logical)
      REMOVE useStandardizedQuery (logical)
      REMOVE useVectorBasemaps (logical)
      REMOVE vectorBasemapGalleryGroupQuery (buffer)
      REMOVE subscriptionInfo.id (buffer)
      REMOVE subscriptionInfo.type (buffer)
      REMOVE subscriptionInfo.state (buffer)
      REMOVE subscriptionInfo.expDate (int64)
      REMOVE subscriptionInfo.userLicenseTypes.creatorUT (int64)
      REMOVE subscriptionInfo.userLicenseTypes.viewerUT (int64)
      REMOVE subscriptionInfo.maxUsersPerLevel.1 (int64)
      REMOVE subscriptionInfo.maxUsersPerLevel.2 (int64)
      REMOVE subscriptionInfo.maxUsers (int64)
      REMOVE subscriptionInfo.availableCredits (real64)
      REMOVE subscriptionInfo.collaborationSettings.level (buffer)
      REMOVE subscriptionInfo.collaborationSettings.maxItemSizeInMB (int64)
      REMOVE subscriptionInfo.collaborationSettings.maxReplicationPackageSizeInMB (int64)
      REMOVE ipCntryCode (buffer)
      REMOVE httpPort (int64)
      REMOVE httpsPort (int64)
      REMOVE supportsOAuth (logical)
      REMOVE currentVersion (buffer)
      REMOVE mfaEnabled (logical)
      REMOVE contacts{} (buffer)
      REMOVE user.username (buffer)
      REMOVE user.udn (buffer)
      REMOVE user.id (buffer)
      REMOVE user.fullName (buffer)
      REMOVE user.firstName (buffer)
      REMOVE user.lastName (buffer)
      REMOVE user.preferredView (buffer)
      REMOVE user.description (buffer)
      REMOVE user.email (buffer)
      REMOVE user.userType (buffer)
      REMOVE user.idpUsername (buffer)
      REMOVE user.favGroupId (buffer)
      REMOVE user.lastLogin (int64)
      REMOVE user.mfaEnabled (logical)
      REMOVE user.storageUsage (int64)
      REMOVE user.storageQuota (int64)
      REMOVE user.orgId (buffer)
      REMOVE user.role (buffer)
      REMOVE user.privileges{} (buffer)
      REMOVE user.level (buffer)
      REMOVE user.userLicenseTypeId (buffer)
      REMOVE user.disabled (logical)
      REMOVE user.culture (buffer)
      REMOVE user.cultureFormat (buffer)
      REMOVE user.region (buffer)
      REMOVE user.units (buffer)
      REMOVE user.thumbnail (buffer)
      REMOVE user.access (buffer)
      REMOVE user.created (int64)
      REMOVE user.modified (int64)
      REMOVE user.provider (buffer)
      REMOVE appInfo.appId (buffer)
      REMOVE appInfo.itemId (buffer)
      REMOVE appInfo.appOwner (buffer)
      REMOVE appInfo.orgId (buffer)
      REMOVE appInfo.appTitle (buffer)
      REMOVE appInfo.privileges{} (buffer)
    -> ParseDataStorePerformance [INITIATOR]
ParseDataStorePerformance: FeatureReader
    ATTRIBUTES = JSONFeature,"ts,value"
    ATTR_ACCUM_MODE = Merge Initiator and Result
    ATTR_CONFLICT_RES = Use Result
    ATTR_IGNORE_NULLS = No
    COMBINE_GEOM = Use Result
    DATASET = @Value(URL)
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    ORDER_RESULTS = No
    OUTPUT_FEATURES_DISPLAY = Schema and Data Features
    JSONFeature -> AttributeManager_8
AttributeManager_8
    ATTR_TABLE:
      SET_TO utchour (varchar(200)) = @DateTimeParse(@Evaluate(@Value(ts)/1000),%s)
      REMOVE ts (int64)
      REMOVE Token (varchar(200))
      REMOVE URL (varchar(200))
      REMOVE id (buffer)
      REMOVE urlKey (buffer)
    -> DataStoreCPU (writer FFS_1)
DataStoreCPU (writer FFS_1)
    attributes: value real64, utchour varchar(200)
