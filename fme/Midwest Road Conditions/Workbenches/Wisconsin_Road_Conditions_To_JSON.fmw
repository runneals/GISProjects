FME workspace Wisconsin_Road_Conditions_To_JSON.fmw
Title: Wisconsin Road Conditions to GeoJSON
Description: This workspace reads data in from the Wisconsin Winter Road Conditions JSON Feed, merges it with the AGOL segment object ID, and writes it out to a json file.
REQUIRED: Obtain a token key for access to the feed here: https://511wi.gov/developers/resources

Parameters:
- DestDataset_JSON = $(FME_MF_DIR)Data\Wisconsin.json   # Destination JSON (JavaScript Object Notation) File
- SourceDataset_JSON = $(FME_MF_DIR)Segment\Wisconsin.json   # Source JSON (JavaScript Object Notation) File or URL
- Wisconsin_JSONFeed = http://www.511wi.gov/web/api/winterroadconditions?key=&format=json   # Source JSON (JavaScript Object Notation) File or URL

Readers:
- JSON_1: JSON from $(Wisconsin_JSONFeed)
- JSON_2: JSON from $(SourceDataset_JSON)

Writers:
- JSON_3: JSON to $(DestDataset_JSON)

Note: Wisconsin Segment Geometry / with AGOL Object IDs
Wisconsin (reader JSON_2)
    attributes: SEGMENT_NAME string, ROUTE_NAME string, SEGMENT_ID string, SOURCE string, SOURCE_LINK string, OBJECTID int, PRIMARYMP string, SECONDARYMP string, HEADLINE string, REPORT_UPDATED string, REPORT_CREATED string, DESCRIPTION string, FMEDATA_READ string, STATUS string, PRIMARYLAT string, PRIMARYLONG string, SECONDARYLAT string, SECONDARYLONG string, REPORT_ID string, AGOL_WRITE string, SHAPE__Length string, ROAD_CONDITION string, SHAPE__Length_2 float, json_ogc_wkt_crs string, json_geometry.type string, json_geometry.coordinates{}.array{} float
    -> Merger [REQUESTOR]
Note: Wisconsin Road Conditions JSON Feed
JSONFeature (reader JSON_1)
    attributes: Condition string, EndCounty string, LocationDescription string, Region string, SegmentCoordinates{}.Latitude float, SegmentCoordinates{}.Longitude float, StartCounty string
    -> Merger [SUPPLIER]
Note: Merge on Segment ID
Merger: FeatureMerger
    REJECT_NULL_MISSING_KEYS = No
    JOIN_KEYS = @Value(SEGMENT_ID) @Value(StartCounty)-@Value(EndCounty)-@Value(Region)-@Value(LocationDescription) AUTO
    PROCESS_DUPS = No
    ATTR_ACCUM_MODE = Merge Supplier
    IGNORE_NULLS = No
    MERGE_TYPE = Attributes Only
    ATTR_CONFLICT_RES = Use Requestor
    SUPPLIERS_FIRST = Yes
    MERGED -> Formatter
Note: Attribute Standardization
Formatter: AttributeManager
    ATTR_TABLE:
      SET_TO HEADLINE = FME_CONDITIONAL:DEFAULT_VALUE'Data Not Available'BOOL_OP;OR;COMPOSITE_TEST;<Unused>;TEST @Value(Condition) = No Information'Data Not Available'BOOL_OP;OR;COMPOSITE_TEST;<Unused>;TEST @Value(Condition) = Travel Not Advised'Travel Not Advised'BOOL_OP;OR;COMPOSITE_TEST;<Unused>;TEST @Value(Condition) = Ice Covered'Completely Covered with Ice'BOOL_OP;OR;COMPOSITE_TEST;<Unused>;TEST @Value(Condition) = Snow Covered'Completely Covered with Snow'BOOL_OP;OR;COMPOSITE_TEST;<Unused>;TEST @Value(Condition) = Slippery Stretches'Partially Covered with Mixed Snow Ice or Slush'BOOL_OP;OR;COMPOSITE_TEST;<Unused>;TEST @Value(Condition) = Good Winter Driving'Seasonal'FME_NUM_CONDITIONS7___
      SET_TO ROAD_CONDITION = FME_CONDITIONAL:DEFAULT_VALUE'Data Not Available'BOOL_OP;OR;COMPOSITE_TEST;<Unused>;TEST @Value(Condition) = No Information'Data Not Available'BOOL_OP;OR;COMPOSITE_TEST;<Unused>;TEST @Value(Condition) = Travel Not Advised'Travel Not Advised'BOOL_OP;OR;COMPOSITE_TEST;<Unused>;TEST @Value(Condition) = Ice Covered;TEST @Value(Condition) = Snow Covered'Completely Covered'BOOL_OP;OR;COMPOSITE_TEST;<Unused>;TEST @Value(Condition) = Slippery Stretches'Partially Covered'BOOL_OP;OR;COMPOSITE_TEST;<Unused>;TEST @Value(Condition) = Good Winter Driving'Seasonal'FME_NUM_CONDITIONS6___
      RENAME_SET_VALUE Condition > DESCRIPTION
      REMOVE EndCounty
      REMOVE LocationDescription
      REMOVE Region
      REMOVE StartCounty
      SET_TO SOURCE = Wisconsin DOT
      SET_TO SOURCE_LINK = http://www.511wi.gov/Web/traffic/map.aspx
      SET_TO STATUS = ACTIVE-CURRENT
      REMOVE json_ogc_wkt_crs
      SET_TO FMEDATA_READ = @DateTimeAdd(@Timestamp(^Y^m^d^H^M^S),PT@Left(@Right(@DateTimeNow(local),4),1)H)
      SET_TO REPORT_UPDATED = @Value(FMEDATA_READ)
      SET_TO REPORT_CREATED = @Value(FMEDATA_READ)
      REMOVE SHAPE__Length_2
      REMOVE json_geometry.type
      REMOVE json_geometry.coordinates{}.array{}
    -> Wisconsin (writer JSON_3)
Note: Write out to JSON
Wisconsin (writer JSON_3)
    attributes: SEGMENT_NAME string, SEGMENT_ID string, PRIMARYMP string, SECONDARYMP string, ROUTE_NAME string, OBJECTID int, SOURCE string, SOURCE_LINK string, FMEDATA_READ string, HEADLINE string, REPORT_UPDATED string, REPORT_CREATED string, DESCRIPTION string, STATUS string, PRIMARYLAT string, PRIMARYLONG string, SECONDARYLAT string, SECONDARYLONG string, REPORT_ID string, AGOL_WRITE string, SHAPE__Length string, ROAD_CONDITION string
