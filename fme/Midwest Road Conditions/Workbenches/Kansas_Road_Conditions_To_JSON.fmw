FME workspace Kansas_Road_Conditions_To_JSON.fmw
Title: Kansas Road Conditions to GeoJSON
Description: This workspace reads data in from the Kansas Winter Road Conditions Service, merges it with the AGOL segment object ID, and writes it out to a json file.
Pulls data from Drive Kansas

Parameters:
- SourceDataset_ARCGISFEATURES_9 = http://www.kandrive.org/arcgis/rest/services/kandrive/StaticMaps/MapServer   # Host
- DestDataset_JSON = $(FME_MF_DIR)Data\Kansas.json   # Destination JSON (JavaScript Object Notation) File
- SourceDataset_JSON = $(FME_MF_DIR)Segment\Kansas.json   # Source JSON (JavaScript Object Notation) File or URL

Readers:
- JSON_1: JSON from $(SourceDataset_JSON)
- ARCGISFEATURES_1: ARCGISFEATURES from $(SourceDataset_ARCGISFEATURES_9)

Writers:
- JSON_2: JSON to $(DestDataset_JSON)

Note: Read in Kansas Road Conditions / from ArcGIS Feature Service
Conditions (reader ARCGISFEATURES_1)
    attributes: ACCOMMODATION esriFieldTypeString(80), ADMIN_OWNER esriFieldTypeString(4), BEG_DESC esriFieldTypeString(200), BEG_POINT_DESC esriFieldTypeString(62), BEG_STATE_LOGMILE esriFieldTypeDouble, CLOSED_COND esriFieldTypeString(1), CLOSED_FROM esriFieldTypeString(80), CLOSED_MSG_SENT esriFieldTypeDouble, CLOSED_TO esriFieldTypeString(80), COUNTY_NO esriFieldTypeInteger, END_DESC esriFieldTypeString(200), END_POINT_DESC esriFieldTypeString(68), END_STATE_LOGMILE esriFieldTypeDouble, GEOMETRY.STLength() esriFieldTypeDouble, LANE_DESCRIPTION esriFieldTypeString(6), LAST_UPDATE esriFieldTypeDate, LINE_COLOR esriFieldTypeDouble, LRS_KEY esriFieldTypeString(28), LRS_PREFIX esriFieldTypeString(4), LRS_SUBCLASS esriFieldTypeString(4), LRS_SUFFIX esriFieldTypeString(4), MSG_CODE esriFieldTypeString(4), MSG_SENT esriFieldTypeString(1), OBJECTID esriFieldTypeOID, RCRS_ROADS_ID esriFieldTypeInteger, RCRSP_DIST esriFieldTypeDouble, RCRSP_VIEW esriFieldTypeInteger, RD_SUFX_SUBC esriFieldTypeString(6), RE_OPENING esriFieldTypeDate, REPORT_TIME esriFieldTypeString(20),
      ROAD_COND_TEXT esriFieldTypeString(100), ROAD_COND_TIME esriFieldTypeString(20), ROAD_CONDITION esriFieldTypeString(6), ROUTE_ID esriFieldTypeString(10), RT_NUMBER esriFieldTypeString(5), SEG_LENGTH_MILES esriFieldTypeDouble, SEGMENT_ID esriFieldTypeString(16), SITE_CR esriFieldTypeString(18), SNICE_BEGIN esriFieldTypeDate, SNICE_END esriFieldTypeDate, SNOW_AREA esriFieldTypeDouble, SNOW_DIST esriFieldTypeDouble, SNOW_ICE_CATEGORY esriFieldTypeDouble, SNOW_SUBAREA esriFieldTypeDouble, STALE_MSG esriFieldTypeString(10), UNIQUE_ID esriFieldTypeString(4), USER_ID esriFieldTypeDouble
    -> DateFormatter
Note: Kansas Segment Geometry / with AGOL Object IDs. / Supplier is FIRST.
Kansas (reader JSON_1)
    attributes: ROUTE_NAME string, SEGMENT_NAME string, PRIMARYMP string, SECONDARYMP string, SOURCE string, SOURCE_LINK string, SEGMENT_ID string, OBJECTID int, json_ogc_wkt_crs string, json_geometry object
    -> SEGMENT_ID [SUPPLIER]
Note: Merger
SEGMENT_ID: FeatureMerger
    ATTR_ACCUM_MODE = Merge Supplier
    ATTR_CONFLICT_RES = Use Requestor
    JOIN_KEYS = @Value(SEGMENT_ID) @Value(SEGMENT_ID) AUTO
    PROCESS_DUPS = No
    IGNORE_NULLS = No
    REJECT_NULL_MISSING_KEYS = No
    MERGE_TYPE = Attributes Only
    SUPPLIERS_FIRST = Yes
    MERGED -> Kansas (writer JSON_2)
Note: Write out to json file with Attributes
Kansas (writer JSON_2)
    attributes: DESCRIPTION string, HEADLINE string, ROUTE_NAME string, SEGMENT_NAME string, PRIMARYMP string, SECONDARYMP string, ROAD_CONDITION string, REPORT_CREATED string, STATUS string, FMEDATA_READ string, SOURCE string, SOURCE_LINK string, REPORT_UPDATED string, OBJECTID string

Bookmark: Date Formatting
DateFormatter
    FMT = FME Date/Time (%Y%m%d%H%M%S)
    SRCFMT = Unknown - Automatic Detection
    DATE_ATTR = ROAD_COND_TIME
    INVALID_DATE_VALUE = _FME_NO_OP_
    -> InterstatePrefixFormat

Bookmark: Format Attributes
Note: Format Interstate Prefix
InterstatePrefixFormat: AttributeCreator
    ATTR_TABLE = SET_TO LRS_PREFIX = FME_CONDITIONAL:DEFAULT_VALUE'@Value(LRS_PREFIX) 'BOOL_OP;OR;COMPOSITE_TEST;<Unused>;TEST @Value(LRS_PREFIX) = I'I-'FME_NUM_CONDITIONS2___
    -> AttributeManager
Note: Standardize Attributes
AttributeManager
    ATTR_TABLE:
      SET_TO FMEDATA_READ = @DateTimeAdd(@Timestamp(^Y^m^d^H^M^S),PT@Left(@Right(@DateTimeNow(local),4),1)H)
      SET_TO validatedtime = @DateTimeDiff(@Value(ROAD_COND_TIME),@Value(FMEDATA_READ),Days)
      SET_TO ROAD_CONDITION = FME_CONDITIONAL:DEFAULT_VALUE'Data Not Available'BOOL_OP;OR;COMPOSITE_TEST;<Unused>;TEST @Value(ROAD_CONDITION) = 3;TEST @Value(ROAD_COND_TEXT) = Normal;TEST @Value(ROAD_COND_TEXT) = Wet/Slush'Seasonal'BOOL_OP;OR;COMPOSITE_TEST;<Unused>;TEST @Value(ROAD_CONDITION) = 7;TEST @Value(ROAD_COND_TEXT) = Spots Snowpacked/Ice;TEST @Value(ROAD_COND_TEXT) = Partly Snowpacked/Ice'Partially Covered'BOOL_OP;OR;COMPOSITE_TEST;<Unused>;TEST @Value(ROAD_CONDITION) = 9;TEST @Value(ROAD_COND_TEXT) = Drifting;TEST @Value(ROAD_COND_TEXT) = Mostly Snowpacked/Ice;TEST @Value(ROAD_COND_TEXT) = Completely Snowpacked/Ice'Completely Covered'BOOL_OP;OR;COMPOSITE_TEST;<Unused>;TEST @Value(ROAD_CONDITION) = 11;TEST @Value(ROAD_CONDITION) = 12;TEST @Value(ROAD_COND_TEXT) = Closed'Impassable'FME_NUM_CONDITIONS5___
      SET_TO DESCRIPTION = FME_CONDITIONAL:DEFAULT_VALUE'@Value(ROAD_COND_TEXT)'BOOL_OP;AND;COMPOSITE_TEST;<Unused>;TEST @Value(CLOSED_FROM) NOT_= _FME_BLANK_STRING_;TEST @Value(CLOSED_TO) NOT_= _FME_BLANK_STRING_'@Value(ROAD_COND_TEXT). CLOSED from @Value(CLOSED_FROM) to @Value(CLOSED_TO).'FME_NUM_CONDITIONS2___
      SET_TO HEADLINE = FME_CONDITIONAL:DEFAULT_VALUE'_FME_NO_OP_'BOOL_OP;OR;COMPOSITE_TEST;<Unused>;TEST @Value(ROAD_CONDITION) = 11;TEST @Value(ROAD_CONDITION) = 12;TEST @Value(ROAD_COND_TEXT) = Closed'Impassable'BOOL_OP;OR;COMPOSITE_TEST;<Unused>;TEST @Value(ROAD_CONDITION) = 9;TEST @Value(ROAD_COND_TEXT) = Mostly Snowpacked/Ice;TEST @Value(ROAD_COND_TEXT) = Completely Snowpacked/Ice'Completely Covered with Mixed Snow Ice or Slush'BOOL_OP;OR;COMPOSITE_TEST;<Unused>;TEST @Value(ROAD_COND_TEXT) = Drifting'Completely Covered with Snow'BOOL_OP;OR;COMPOSITE_TEST;<Unused>;TEST @Value(ROAD_CONDITION) = 7;TEST @Value(ROAD_COND_TEXT) = Spots Snowpacked/Ice;TEST @Value(ROAD_COND_TEXT) = Partly Snowpacked/Ice'Partially Covered with Mixed Snow Ice or Slush'BOOL_OP;OR;COMPOSITE_TEST;<Unused>;TEST @Value(ROAD_CONDITION) = 3;TEST @Value(ROAD_COND_TEXT) = Normal'Seasonal'BOOL_OP;OR;COMPOSITE_TEST;<Unused>;TEST @Value(ROAD_COND_TEXT) = Wet/Slush'Wet'FME_NUM_CONDITIONS7___
      SET_TO ROUTE_NAME = @Value(LRS_PREFIX)-@Value(RT_NUMBER)
      REMOVE LRS_PREFIX
      REMOVE RT_NUMBER
      SET_TO SEGMENT_NAME = @Value(ROUTE_NAME) from @Value(BEG_DESC) (@Value(BEG_POINT_DESC)) to @Value(END_DESC) (@Value(END_POINT_DESC)).
      RENAME_SET_VALUE BEG_STATE_LOGMILE > PRIMARYMP
      RENAME_SET_VALUE END_STATE_LOGMILE > SECONDARYMP
      REMOVE BEG_DESC
      REMOVE END_DESC
      REMOVE ROAD_COND_TEXT
      REMOVE BEG_POINT_DESC
      REMOVE END_POINT_DESC
      REMOVE CLOSED_FROM
      REMOVE CLOSED_TO
      RENAME_SET_VALUE ROAD_COND_TIME > REPORT_CREATED = @DateTimeAdd(@Value(REPORT_CREATED),PT@Left(@Right(@DateTimeNow(local),4),1)H)
      SET_TO STATUS = FME_CONDITIONAL:DEFAULT_VALUE'ACTIVE-CURRENT'BOOL_OP;OR;COMPOSITE_TEST;<Unused>;TEST @Value(validatedtime) <= -2'ACTIVE-STALE'FME_NUM_CONDITIONS2___
      SET_TO SOURCE = Kansas DOT
      SET_TO SOURCE_LINK = http://www.kandrive.org
      SET_TO REPORT_UPDATED = @Value(REPORT_CREATED)
      SET_TO SEGMENT_ID = KS@Value(OBJECTID)
      REMOVE OBJECTID
    -> SEGMENT_ID [REQUESTOR]
