FME workspace Minnesota_Road_Conditions_To_JSON.fmw
Title: Minnesota Road Conditions to GeoJSON
Description: This FME job reads the CARS 511 feed for Minnesota Road Conditions and writes them to a local JSON.
REQUIRED: Obtain XML feed credentials here: https://iowadot.gov/511/xmlrequestform

Parameters:
- SourceDataset_XML = http://mn.carsprogram.org/hub/data/feu-g.xml   # Source XML File(s)
- DestDataset_JSON = $(FME_MF_DIR)Data\Minnesota.json   # Destination JSON (JavaScript Object Notation) File
- SourceDataset_JSON = $(FME_MF_DIR)Segment\Minnesota.json   # Source JSON (JavaScript Object Notation) File or URL
- UTC_Offset = 6   # UTC Offset

Readers:
- XML_1: XML from $(SourceDataset_XML)
- JSON_1: JSON from $(SourceDataset_JSON)

Writers:
- JSON_2: JSON to $(DestDataset_JSON)

Note: Filter out only Road Conditions
Filter_Road_Conditions: TestFilter
    DEFAULT_VALUE = <UNFILTERED>
    TEST_LIST = BOOL_OP,OR,COMPOSITE_TEST,<Unused>,TEST_CLAUSE,"TEST @Value(OrganizationID) CONTAINS MNSEG",MN Road Conditions
    MN Road Conditions -> DateTimeFormat
Note: Date/Time Formatting
DateTimeFormat: AttributeManager
    ATTR_TABLE:
      SET_TO FMEDATA_READ = @Left(@DateTimeNow(utc),14)
      SET_TO REPORT_UPDATED = @DateTimeAdd(@Value(UpdateTimeDate)@Value(UpdateTimeTime),PT@Left(@Right(@DateTimeNow(local),4),1)H)
      SET_TO REPORT_CREATED = @DateTimeAdd(@Value(MessageIssueDate)@Value(MessageIssueTime),PT@Left(@Right(@DateTimeNow(local),4),1)H)
      SET_TO validatedtime = @DateTimeDiff(@Value(REPORT_CREATED),@Value(FMEDATA_READ),Days)
      SET_TO STATUS = FME_CONDITIONAL:DEFAULT_VALUE'ACTIVE-CURRENT'BOOL_OP;OR;COMPOSITE_TEST;<Unused>;TEST @Value(validatedtime) <= -2'ACTIVE-STALE'FME_NUM_CONDITIONS2___
      REMOVE MessageIssueDate
      REMOVE MessageIssueTime
      REMOVE UpdateTimeDate
      REMOVE UpdateTimeTime
    -> Merger [CARS]
Note: Minnesota Segment Geometry / with AGOL Object IDs
Minnesota (reader JSON_1)
    attributes: SEGMENT_NAME string, PRIMARYMP string, PRIMARYLAT string, PRIMARYLONG string, SECONDARYMP string, SECONDARYLAT string, SECONDARYLONG string, ROUTE_NAME string, SOURCE string, SEGMENT_OID string, OBJECTID int, SEGMENT_ID string, json_ogc_wkt_crs string, json_geometry object
    -> Merger [GEOM]
    -> NullMerger [GEOM]
Note: Attempt to Merge attributes / with AGOL Object IDs
Merger: InlineQuerier
    QUERY_DEF:
      Merging,SELECT *
      FROM GEOM, CARS
      WHERE (GEOM.ROUTE_NAME=CARS.RouteDesignator) AND (GEOM.PRIMARYMP BETWEEN CARS.LinearReference1 AND CARS.LinearReference2) AND (GEOM.SECONDARYMP BETWEEN CARS.LinearReference1 AND CARS.LinearReference2);,FIRST,No Data,SELECT count(*) as count FROM CARS;,FIRST
    QUERY_SCHEMA = Merging,PRIMARYMP,"real(31,15)",SECONDARYMP,"real(13,8)",ROUTE_NAME,text,GEOM.fme_feature_content,fme_feature_content,LinearReference1,varchar(200),LinearReference2,varchar(200),RouteDesignator,text,REPORT_UPDATED,text,REPORT_CREATED,text,CARS.fme_feature_content,fme_feature_content,No Data,count,
    TABLE_DEF = GEOM,PRIMARYMP,"real(31,15)",SECONDARYMP,"real(13,8)",ROUTE_NAME,text,CARS,LinearReference1,varchar(200),LinearReference2,varchar(200),RouteDesignator,text,REPORT_UPDATED,text,REPORT_CREATED,text
    Merging -> AttributeManager
    No Data -> CountTester
Note: Write out to json file with attributes
Minnesota (writer JSON_2)
    attributes: ROAD_CONDITION string, SOURCE_LINK string, PRIMARYMP string, SECONDARYMP string, ROUTE_NAME string, SEGMENT_NAME string, SEGMENT_ID string, SEGMENT_OID string, PRIMARYLAT string, PRIMARYLONG string, SECONDARYLAT string, SECONDARYLONG string, REPORT_UPDATED string, REPORT_CREATED string, REPORT_ID string, HEADLINE string, DESCRIPTION string, FMEDATA_READ string, STATUS string, SOURCE string, OBJECTID int

Bookmark: MINNESOTA 511 XML FEED
  Connection for MN CARS 511 Production XML Feed (http://mn.carsprogram.org/hub/data/feu-g.xml )
Feature (reader XML_1)
    attributes: Descriptions xml_char(553), ID xml_char(15), LinearReference1 xml_decimal(31,19), LinearReference2 xml_decimal(22,18), LinkDirection xml_char(19), MessageIssueDate xml_decimal(9,0), MessageIssueTime xml_decimal(7,0), OrganizationID xml_char(14), RouteDesignator xml_char(22), UpdateTimeDate xml_decimal(9,0), UpdateTimeTime xml_decimal(7,0), hd_pavementcond xml_char(26), ph_pavementcond xml_char(26), AltRoute xml_char(25), CrossRoad1 xml_char(16), CrossRoad2 xml_char(19), EndTimeDate xml_decimal(9,0), EndTimeTime xml_decimal(7,0), EndTimeUTCoffset xml_decimal(6,0), Instructions xml_char(18), Latitude1 xml_decimal(9,0), Latitude2 xml_decimal(9,0), Longitude1 xml_decimal(10,0), Longitude2 xml_decimal(10,0), MessageExpiryDate xml_decimal(9,0), MessageExpiryTime xml_decimal(7,0), MessageIssueUTCoffset xml_decimal(6,0), MessageNumber xml_decimal(11,0), Ownership xml_char(11), Priority xml_decimal(3,0),
      RestrictionHeight xml_decimal(4,0), RestrictionLength xml_decimal(5,0), RestrictionWeightVehicle xml_decimal(6,0), RestrictionWidth xml_decimal(4,0), SpeedLimit xml_decimal(3,0), StartTimeDate xml_decimal(9,0), StartTimeTime xml_decimal(7,0), StartTimeUTCoffset xml_decimal(6,0), Status xml_char(8), Update xml_decimal(5,0), UpdateTimeUTCoffset xml_decimal(6,0), Warnings xml_char(45), ca_mobsit xml_char(30), ca_obstruction xml_char(9), ca_roadwork xml_char(29), hd_closure xml_char(26), hd_incident xml_char(16), hd_restriction xml_char(19), hd_roadwork xml_char(43), hd_specialevent xml_char(7), hd_systeminfo xml_char(13), ph_closure xml_char(48), ph_delay xml_char(29), ph_incident xml_char(9), ph_restriction xml_char(36), ph_roadwork xml_char(30), ph_specialevent xml_char(7), ph_systeminfo xml_char(13), ph_traffic xml_char(13)
    -> Filter_Road_Conditions

Bookmark: Merged Records
Note: Standardize Attributes
AttributeManager
    ATTR_TABLE:
      SET_TO ROAD_CONDITION = FME_CONDITIONAL:DEFAULT_VALUE'Data Not Available'BOOL_OP;OR;COMPOSITE_TEST;<Unused>;TEST @Value(hd_pavementcond) = dry pavement;TEST @Value(hd_pavementcond) = wet;TEST @Value(hd_pavementcond) = seasonal roadway conditions;TEST @Value(hd_pavementcond) = seasonal;TEST @Value(hd_pavementcond) = Seasonal;TEST @Value(hd_pavementcond) = normal driving conditions'Seasonal'BOOL_OP;OR;COMPOSITE_TEST;<Unused>;TEST @Value(hd_pavementcond) = impassable;TEST @Value(hd_pavementcond) = Impassable'Impassable'BOOL_OP;OR;COMPOSITE_TEST;<Unused>;TEST @Value(hd_pavementcond) = travel not advised;TEST @Value(ph_pavementcond) = travel not advised'Travel Not Advised'BOOL_OP;OR;COMPOSITE_TEST;<Unused>;TEST @Value(hd_pavementcond) BEGINS_WITH completely'Completely Covered'BOOL_OP;OR;COMPOSITE_TEST;<Unused>;TEST @Value(hd_pavementcond) BEGINS_WITH partially;TEST @Value(hd_pavementcond) = icy bridges'Partially Covered'FME_NUM_CONDITIONS6___
      SET_TO SOURCE = Minnesota DOT
      SET_TO SOURCE_LINK = http://hb.511mn.org/#roadReports/eventAlbum/@Value(ID)?timeFrame=TODAY&layers=winterDriving
      REMOVE LinearReference1
      REMOVE LinearReference2
      REMOVE RouteDesignator
      REMOVE Descriptions
      RENAME_SET_VALUE ID > REPORT_ID
      REMOVE LinkDirection
      REMOVE OrganizationID
      RENAME_SET_VALUE hd_pavementcond > HEADLINE
      RENAME_SET_VALUE ph_pavementcond > DESCRIPTION
    -> Minnesota (writer JSON_2)

Bookmark: No Merged Records - Null out segments
CountTester: Tester
    TEST_DESCRIPTION = Test if sql count has 0 records
    BOOL_OP = OR
    TEST_MODE = Automatic
    TEST_CLAUSE = TEST @Value(count) = 0
    PASSED -> NullMerger [Count]
NullMerger: InlineQuerier
    QUERY_DEF = Merging,SELECT * FROM GEOM, Count WHERE Count.count = '0';,FIRST
    QUERY_SCHEMA = Merging,PRIMARYMP,"real(31,15)",SECONDARYMP,"real(13,8)",ROUTE_NAME,text,GEOM.fme_feature_content,fme_feature_content,count,varchar(200),Count.fme_feature_content,fme_feature_content
    TABLE_DEF = GEOM,PRIMARYMP,"real(31,15)",SECONDARYMP,"real(13,8)",ROUTE_NAME,text,Count,count,varchar(200)
    Merging -> AttributeManager_2
Note: Standardize Attributes
AttributeManager_2
    ATTR_TABLE:
      SET_TO ROAD_CONDITION = 0
      SET_TO SOURCE = Minnesota DOT
      SET_TO SOURCE_LINK = http://hb.511mn.org
      REMOVE SOURCE
      SET_TO HEADLINE = FME_NULL_VALUE
      SET_TO DESCRIPTION = FME_NULL_VALUE
      SET_TO REPORT_ID = FME_NULL_VALUE
      SET_TO REPORT_UPDATED = FME_NULL_VALUE
      SET_TO REPORT_CREATED = FME_NULL_VALUE
      SET_TO FMEDATA_READ = @Timestamp(^Y^m^d^H^M^S)
    -> Minnesota (writer JSON_2)
