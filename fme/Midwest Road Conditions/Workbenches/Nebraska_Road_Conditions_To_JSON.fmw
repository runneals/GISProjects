FME workspace Nebraska_Road_Conditions_To_JSON.fmw
Title: Nebraska Road Conditions to GeoJSON
Description: This FME job reads the CARS 511 feed for Nebraska Road Conditions and writes them to a local JSON file. 
REQUIRED: Obtain XML feed credentials here: https://iowadot.gov/511/xmlrequestform

Parameters:
- SourceDataset_XML_9 = http://ne.carsprogram.org/hub/data/feu-g.xml   # Source XML File(s)
- SourceDataset_JSON = $(FME_MF_DIR)Segment\Nebraska.json   # Source JSON (JavaScript Object Notation) File or URL
- DestDataset_JSON_4 = $(FME_MF_DIR)Data\Nebraska.json   # Destination JSON (JavaScript Object Notation) File
- UTC_Offset = 6   # UTC Offset

Readers:
- XML_1: XML from $(SourceDataset_XML_9)
- JSON_1: JSON from $(SourceDataset_JSON)

Writers:
- JSON_2: JSON to $(DestDataset_JSON_4)

Note: Filter out only Road Conditions
Filter_Road_Conditions: TestFilter
    TEST_LIST = BOOL_OP,OR,COMPOSITE_TEST,<Unused>,TEST_CLAUSE,"TEST @Value(OrganizationID) CONTAINS NESEG",NE Road Conditions
    DEFAULT_VALUE = <UNFILTERED>
    NE Road Conditions -> DateTimeFormat
Note: Date/Time + Length formatting
DateTimeFormat: AttributeManager
    ATTR_TABLE:
      SET_TO FMEDATA_READ = @DateTimeAdd(@Timestamp(^Y^m^d^H^M^S),PT@Left(@Right(@DateTimeNow(local),4),1)H)
      SET_TO REPORT_UPDATED = @DateTimeAdd(@Value(UpdateTimeDate)@Value(UpdateTimeTime),PT@Right(@Left(@Value(UpdateTimeUTCoffset),3),1)H)
      SET_TO REPORT_CREATED = @DateTimeAdd(@Value(MessageIssueDate)@Value(MessageIssueTime),PT@Right(@Left(@Value(MessageIssueUTCoffset),3),1)H)
    -> InlineQuerier [CARS]
Note: Nebraska Segment Geometry / with AGOL Objects IDs
Nebraska (reader JSON_1)
    attributes: SEGMENT_NAME string, SEGMENT_OID string, PRIMARYMP string, PRIMARYLAT string, PRIMARYLONG string, SECONDARYMP string, SECONDARYLAT string, SECONDARYLONG string, ROUTE_NAME string, SEGMENT_DATE string, SOURCE string, OBJECTID int, SEGMENT_ID string, json_ogc_wkt_crs string, json_geometry object
    -> InlineQuerier [GEOM]
    -> NullMerger [GEOM]
Note: Attempt to Merge attributes / with AGOL Object IDs
InlineQuerier
    QUERY_DEF:
      Merging,SELECT *
      FROM GEOM, CARS
      WHERE (GEOM.ROUTE_NAME=CARS.RouteDesignator) AND (GEOM.PRIMARYMP BETWEEN CARS.LinearReference1 AND CARS.LinearReference2) AND (GEOM.SECONDARYMP BETWEEN CARS.LinearReference1 AND CARS.LinearReference2);,FIRST,No Data,SELECT count(*) as count FROM CARS;,FIRST
    QUERY_SCHEMA = Merging,PRIMARYMP,"real(6,2)",SECONDARYMP,"real(6,2)",ROUTE_NAME,text,GEOM.fme_feature_content,fme_feature_content,LinearReference1,"real(6,2)",LinearReference2,"real(6,2)",RouteDesignator,text,REPORT_UPDATED,text,REPORT_CREATED,text,CARS.fme_feature_content,fme_feature_content,No Data,count,
    TABLE_DEF = GEOM,PRIMARYMP,"real(6,2)",SECONDARYMP,"real(6,2)",ROUTE_NAME,text,CARS,LinearReference1,"real(6,2)",LinearReference2,"real(6,2)",RouteDesignator,text,REPORT_UPDATED,text,REPORT_CREATED,text
    Merging -> AttributeManager
    No Data -> CountTester
Note: Write out to json file with attributes
Nebraska (writer JSON_2)
    attributes: ROAD_CONDITION string, SOURCE string, SOURCE_LINK string, PRIMARYMP string, SECONDARYMP string, ROUTE_NAME string, SEGMENT_NAME string, SEGMENT_ID string, SEGMENT_OID string, PRIMARYLAT string, PRIMARYLONG string, SECONDARYLAT string, SECONDARYLONG string, REPORT_UPDATED string, REPORT_CREATED string, REPORT_ID string, HEADLINE string, DESCRIPTION string, FMEDATA_READ string, STATUS string, SEGMENT_DATE string, OBJECTID int

Bookmark: NEBRASKA 511 XML FEED
  Connection for NE CARS 511 Production XML Feed (http://ne.carsprogram.org/hub/data/feu-g.xml )
Feature (reader XML_1)
    attributes: ID xml_char(13), LinkDirection xml_char(19), MessageIssueDate xml_decimal(9,0), MessageIssueTime xml_decimal(7,0), RouteDesignator xml_char(12), UpdateTimeDate xml_decimal(9,0), UpdateTimeTime xml_decimal(7,0), hd_pavementcond xml_char(31), ph_pavementcond xml_char(31), LinearReference1 xml_decimal(31,18), LinearReference2 xml_decimal(19,15), Descriptions xml_char(374), OrganizationID xml_char(8), Latitude1 xml_decimal(9,0), Latitude2 xml_decimal(9,0), MessageNumber xml_decimal(7,0), CrossRoad1 xml_char(8), EndTimeDate xml_decimal(9,0), EndTimeTime xml_decimal(7,0), EndTimeUTCoffset xml_decimal(6,0), MessageExpiryDate xml_decimal(9,0), MessageExpiryTime xml_decimal(7,0), MessageIssueUTCoffset xml_decimal(6,0), Ownership xml_char(11), Priority xml_decimal(3,0), RestrictionLength xml_decimal(5,0), RestrictionWidth xml_decimal(4,0), SpeedLimit xml_decimal(3,0), StartTimeDate xml_decimal(9,0), StartTimeTime xml_decimal(7,0),
      StartTimeUTCoffset xml_decimal(6,0), Status xml_char(8), Update xml_decimal(4,0), UpdateTimeUTCoffset xml_decimal(6,0), Warnings xml_char(21), hd_closure xml_char(20), hd_mobsit xml_char(32), hd_obstruction xml_char(11), hd_restriction xml_char(13), hd_roadwork xml_char(28), hd_systeminfo xml_char(13), ph_closure xml_char(26), ph_mobsit xml_char(32), ph_obstruction xml_char(11), ph_restriction xml_char(13), ph_roadwork xml_char(28), ph_systeminfo xml_char(13), Longitude1 xml_decimal(11,0), ca_roadwork xml_char(28), Longitude2 xml_decimal(11,0), ca_pavementcond xml_char(31)
    -> Filter_Road_Conditions

Bookmark: Merged Records
Note: Standardize Attributes
AttributeManager
    ATTR_TABLE:
      SET_TO ROAD_CONDITION = FME_CONDITIONAL:DEFAULT_VALUE'Data Not Available'BOOL_OP;OR;COMPOSITE_TEST;<Unused>;TEST @Value(hd_pavementcond) = dry pavement;TEST @Value(hd_pavementcond) = wet;TEST @Value(hd_pavementcond) = seasonal roadway conditions;TEST @Value(hd_pavementcond) = seasonal;TEST @Value(hd_pavementcond) = Seasonal;TEST @Value(hd_pavementcond) = normal driving conditions'Seasonal'BOOL_OP;OR;COMPOSITE_TEST;<Unused>;TEST @Value(hd_pavementcond) = impassable;TEST @Value(hd_pavementcond) = Impassable'Impassable'BOOL_OP;OR;COMPOSITE_TEST;<Unused>;TEST @Value(hd_pavementcond) = travel not advised;TEST @Value(ph_pavementcond) = travel not advised'Travel Not Advised'BOOL_OP;OR;COMPOSITE_TEST;<Unused>;TEST @Value(hd_pavementcond) BEGINS_WITH completely'Completely Covered'BOOL_OP;OR;COMPOSITE_TEST;<Unused>;TEST @Value(hd_pavementcond) BEGINS_WITH partially;TEST @Value(hd_pavementcond) = icy bridges'Partially Covered'FME_NUM_CONDITIONS6___
      SET_TO SOURCE = Nebraska DOT
      SET_TO SOURCE_LINK = https://hb.511.nebraska.gov/#roadReports/eventAlbum/@Value(ID)?timeFrame=TODAY&layers=winterDriving
      REMOVE LinearReference1
      REMOVE LinearReference2
      REMOVE RouteDesignator
      REMOVE Descriptions
      RENAME_SET_VALUE ID > REPORT_ID
      REMOVE LinkDirection
      REMOVE MessageIssueDate
      REMOVE MessageIssueTime
      REMOVE OrganizationID
      REMOVE UpdateTimeDate
      REMOVE UpdateTimeTime
      RENAME_SET_VALUE hd_pavementcond > HEADLINE
      RENAME_SET_VALUE ph_pavementcond > DESCRIPTION
    -> Nebraska (writer JSON_2)

Bookmark: No Merged Records - Null out segments
CountTester: Tester
    TEST_CLAUSE = TEST @Value(count) = 0
    BOOL_OP = OR
    TEST_MODE = Automatic
    TEST_DESCRIPTION = Test if sql count has 0 records
    PASSED -> NullMerger [Count]
NullMerger: InlineQuerier
    QUERY_DEF = Merging,SELECT * FROM GEOM, Count WHERE Count.count = '0';,FIRST
    QUERY_SCHEMA = Merging,PRIMARYMP,"real(31,15)",SECONDARYMP,"real(13,8)",ROUTE_NAME,text,GEOM.fme_feature_content,fme_feature_content,count,varchar(200),Count.fme_feature_content,fme_feature_content
    TABLE_DEF = GEOM,PRIMARYMP,"real(31,15)",SECONDARYMP,"real(13,8)",ROUTE_NAME,text,Count,count,varchar(200)
    Merging -> AttributeManager_3
Note: Standardize Attributes
AttributeManager_3
    ATTR_TABLE:
      SET_TO ROAD_CONDITION = 0
      SET_TO SOURCE = Nebraska DOT
      SET_TO SOURCE_LINK = https://hb.511.nebraska.gov
      REMOVE SOURCE
      SET_TO HEADLINE = FME_NULL_VALUE
      SET_TO DESCRIPTION = FME_NULL_VALUE
      SET_TO REPORT_ID = FME_NULL_VALUE
      SET_TO REPORT_UPDATED = FME_NULL_VALUE
      SET_TO REPORT_CREATED = FME_NULL_VALUE
      SET_TO FMEDATA_READ = @Timestamp(^Y^m^d^H^M^S)
    -> Nebraska (writer JSON_2)
