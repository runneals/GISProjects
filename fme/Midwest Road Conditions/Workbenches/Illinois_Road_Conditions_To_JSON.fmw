FME workspace Illinois_Road_Conditions_To_JSON.fmw
Title: Illinois Road Conditions to GeoJSON
Description: This workspace reads data in from the Illinois Winter Road Conditions Service, merges it with the AGOL segment object ID, and writes it out to a json file.

Parameters:
- DestDataset_JSON = $(FME_MF_DIR)Data\Illinois.json   # Destination JSON (JavaScript Object Notation) File
- SourceDataset_JSON = $(FME_MF_DIR)Segment\Illinois.json   # Source JSON (JavaScript Object Notation) File or URL
- SourceDataset_ARCGISFEATURES_3 = http://services2.arcgis.com/aIrBD8yn1TDTEXoz/ArcGIS/rest/services/Winter_Road_Conditions/FeatureServer   # Host

Readers:
- JSON_1: JSON from $(SourceDataset_JSON)
- ARCGISFEATURES_1: ARCGISFEATURES from $(SourceDataset_ARCGISFEATURES_3)

Writers:
- JSON_2: JSON to $(DestDataset_JSON)

Note: Read in Illinois Road Conditions / from ArcGIS Feature Service
WinterRoadConditions (reader ARCGISFEATURES_1)
    attributes: OBJECTID_12 esriFieldTypeInteger, OBJECTID esriFieldTypeDouble, COND_ID esriFieldTypeString(40), RD_COND esriFieldTypeDouble, TOLLWAY esriFieldTypeDouble, YARDS esriFieldTypeString(10), Id esriFieldTypeInteger, Route esriFieldTypeString(25), County esriFieldTypeString(25), Cond_Desc esriFieldTypeString(100), RPT_DESC esriFieldTypeString(150), DISTRICT esriFieldTypeSmallInteger, LastUpdate esriFieldTypeString(50), Shape__Length esriFieldTypeDouble
    -> AttributeTrimmer
Note: Test for Segment ID
SEGMENT_ID_Test: Tester
    TEST_CLAUSE = TEST @Value(SEGMENT_ID) ATTRIBUTE_HAS_VALUE ""
    BOOL_OP = OR
    TEST_MODE = Automatic
    TEST_DESCRIPTION = ""
    PASSED -> SEGMENT_ID [REQUESTOR]
    FAILED -> SEGMENT_NAME [REQUESTOR]
Note: Illinois Segment Geometry / with AGOL Object IDs. / Supplier is FIRST
Illinois (reader JSON_1)
    attributes: SEGMENT_ID string, SEGMENT_NAME string, ROUTE_NAME string, SOURCE string, SOURCE_LINK string, OBJECTID int, PRIMARYMP string, SECONDARYMP string, HEADLINE string, REPORT_UPDATED string, REPORT_CREATED string, DESCRIPTION string, FMEDATA_READ string, STATUS string, PRIMARYLAT string, PRIMARYLONG string, SECONDARYLAT string, SECONDARYLONG string, REPORT_ID string, AGOL_WRITE string, SHAPE__Length string, ROAD_CONDITION string, SHAPE__Length_2 float, json_ogc_wkt_crs string, json_geometry.type string, json_geometry.coordinates{}.array{} float, json_geometry.coordinates{}.array{}.array{} float
    -> SEGMENT_ID [SUPPLIER]
    -> SEGMENT_NAME [SUPPLIER]
Note: Write out to json file with Attributes
Illinois (writer JSON_2)
    attributes: SEGMENT_ID string, HEADLINE string, ROAD_CONDITION string, SEGMENT_NAME string, DESCRIPTION string, ROUTE_NAME string, REPORT_CREATED string, FMEDATA_READ string, STATUS string, SOURCE string, SOURCE_LINK string, REPORT_UPDATED string, OBJECTID int, PRIMARYMP string, SECONDARYMP string

Bookmark: Format Attributes
AttributeTrimmer
    SRC_ATTRS = Route,RPT_DESC
    TRIM_TO_NONE = Yes
    TRIM_CHARS = " "
    TRIM_TYPE = Both
    -> StringReplacer
Note: Remove "was reported" / from description.
StringReplacer
    REGEXP = NO
    SRC_ATTRS = RPT_DESC
    CASE = NO
    FIND_TEXT = " was reported"
    NO_MATCH = _FME_NO_OP_
    -> AttributeManager
Note: Standardize formatting
AttributeManager
    ATTR_TABLE:
      SET_TO REPORT_CREATED = @DateTimeAdd(@DateTimeParse(@Value(LastUpdate),%I:%M%p %m-%d-%Y),PT@Left(@Right(@DateTimeNow(local),4),1)H)
      REMOVE LastUpdate
      SET_TO REPORT_UPDATED = @Value(REPORT_CREATED)
      SET_TO FMEDATA_READ = @DateTimeAdd(@Timestamp(^Y^m^d^H^M^S),PT@Left(@Right(@DateTimeNow(local),4),1)H)
      SET_TO validatedtime = @DateTimeDiff(@Value(REPORT_CREATED),@Value(FMEDATA_READ),Days)
      SET_TO SEGMENT_ID = @Value(COND_ID)
      SET_TO HEADLINE = FME_CONDITIONAL:DEFAULT_VALUE'Data Not Available'BOOL_OP;OR;COMPOSITE_TEST;<Unused>;TEST @Value(Cond_Desc) = Clear'Seasonal'BOOL_OP;OR;COMPOSITE_TEST;<Unused>;TEST @Value(Cond_Desc) = Partly Covered with ice/snow;TEST @Value(Cond_Desc) = Partly Covered with ice or snow'Partially Covered with Mixed Snow Ice or Slush'BOOL_OP;OR;COMPOSITE_TEST;<Unused>;TEST @Value(Cond_Desc) = Covered with ice/snow;TEST @Value(Cond_Desc) = Mostly Covered with ice/snow'Completely Covered with Mixed Snow Ice or Slush'BOOL_OP;OR;COMPOSITE_TEST;<Unused>;TEST @Value(Cond_Desc) = Covered with ice/snow;TEST @Value(Cond_Desc) = Covered with ice or snow;TEST @Value(Cond_Desc) = Mostly Covered with ice/snow;TEST @Value(Cond_Desc) = Mostly Covered with ice or snow'Completely Covered with Mixed Snow Ice or Slush'FME_NUM_CONDITIONS5___
      SET_TO ROAD_CONDITION = FME_CONDITIONAL:DEFAULT_VALUE'Data Not Available'BOOL_OP;OR;COMPOSITE_TEST;<Unused>;TEST @Value(Cond_Desc) = Clear'Seasonal'BOOL_OP;OR;COMPOSITE_TEST;<Unused>;TEST @Value(Cond_Desc) = Partly Covered with ice/snow;TEST @Value(Cond_Desc) = Partly Covered with ice or snow;TEST @Value(Cond_Desc) CONTAINS Partly Covered'Partially Covered'BOOL_OP;OR;COMPOSITE_TEST;<Unused>;TEST @Value(Cond_Desc) = Covered with ice/snow;TEST @Value(Cond_Desc) CONTAINS Covered;TEST @Value(Cond_Desc) = Mostly Covered with ice/snow;TEST @Value(Cond_Desc) CONTAINS Mostly Covered'Completely Covered'FME_NUM_CONDITIONS4___
      SET_TO SEGMENT_NAME = @Value(Route) @Value(RPT_DESC)
      RENAME_SET_VALUE Cond_Desc > DESCRIPTION
      REMOVE RPT_DESC
      SET_TO STATUS = FME_CONDITIONAL:DEFAULT_VALUE'ACTIVE-CURRENT'BOOL_OP;OR;COMPOSITE_TEST;<Unused>;TEST @Value(validatedtime) <= -2'ACTIVE-STALE'FME_NUM_CONDITIONS2___
      SET_TO SOURCE = Illinois DOT
      SET_TO SOURCE_LINK = http://www.gettingaroundillinois.com/winterconditions/
      REMOVE OBJECTID
      REMOVE OBJECTID_12
      REMOVE TOLLWAY
      REMOVE YARDS
      REMOVE Id
      RENAME_SET_VALUE Route > ROUTE_NAME
      REMOVE Shape__Length
    -> SEGMENT_ID_Test

Bookmark: Mergers
SEGMENT_ID: FeatureMerger
    JOIN_KEYS = @Value(SEGMENT_ID) @Value(SEGMENT_ID) AUTO
    ATTR_CONFLICT_RES = Use Requestor
    SUPPLIERS_FIRST = Yes
    MERGE_TYPE = Attributes Only
    IGNORE_NULLS = No
    ATTR_ACCUM_MODE = Merge Supplier
    REJECT_NULL_MISSING_KEYS = No
    PROCESS_DUPS = No
    MERGED -> Illinois (writer JSON_2)
SEGMENT_NAME: FeatureMerger
    JOIN_KEYS = @Value(SEGMENT_NAME) @Value(SEGMENT_NAME) AUTO
    ATTR_CONFLICT_RES = Use Requestor
    SUPPLIERS_FIRST = Yes
    MERGE_TYPE = Attributes Only
    IGNORE_NULLS = No
    ATTR_ACCUM_MODE = Merge Supplier
    REJECT_NULL_MISSING_KEYS = No
    PROCESS_DUPS = No
    MERGED -> Illinois (writer JSON_2)
