FME workspace JSONs_to_AGOL.fmw
Title: JSONs to AGOL
Description: Writes road conditions to AGOL.
History: 01/2017,D Runneals,Workspace Created,06/2017,D Runneals,Updated to 2017.1 + Documentation
Startup Python:
      #-------------------------------------------------------------------------------
      # Name:        Disables/ReEnables Editing for Service
      # Purpose:
      #
      # Author:      Kelly Gerrow/Hunter Praska/Mark McCart
      #Contact:      kgerrow@esri.com
      #
      # Created:     9/8/2016
      #-------------------------------------------------------------------------------

      def getToken(adminUser, pw):
              data = {'username': adminUser,
                  'password': pw,
                  'referer' : 'https://www.arcgis.com',
                  'f': 'json'}
              url  = 'https://arcgis.com/sharing/rest/generateToken'
              jres = requests.post(url, data=data, verify=False).json()
              return jres['token'],jres['ssl']

      #generates account information
      def GetAccount(pref, tokenfun):
          URL= pref+'www.arcgis.com/sharing/rest/portals/self?f=json&token=' + tokenfun
          response = requests.get(URL, verify=False)
          jres = json.loads(response.text)
          return jres['urlKey']


      import requests, json

      #Enter Username and Password
      user= "USERNAME" #raw_input('What is the ArcGIS Online Username?')
      pw = "PASSWORD" #raw_input('What is the ArcGIS Online Password?')

      #get account information
      token= getToken(user, pw)
      if token[1] == False:
                 pref='http://'
      else:
                 pref='https://'
      #Create Portal URL
      t=GetAccount(pref,token[0])
      portalUrl=pref+t


      restURL='http://services.arcgis.com/8lRhdTsQyJpO52F1/arcgis/rest/admin/services/MidwestWinterRoadConditions/FeatureServer/updateDefinition' #modify URL
      defCapabilities= '{"hasStaticData":false,"capabilities":"Query,Editing,Create,Update,Delete,Extract"}' #editing enabled
      #defCapabilities= '{"capabilities":"Query"}' #editing disabled
      data = {'updateDefinition': defCapabilities,
                  'token':token[0],
                  'f': 'json'}

      #Send Request
      res =requests.post(restURL, data = data, verify=False).json()
      print res
      if res['success']==True:
          print 'Service successfully Added'
      else:
          print 'Service NOT ADDED'
Shutdown Python:
      #-------------------------------------------------------------------------------
      # Name:        Disables/ReEnables Editing for Service & Writes Feature Collections to AGOL
      # Purpose:
      #
      # Authors:     Kelly Gerrow (Esri); Mark McCart (HNTB); Hunter Praska (Iowa DOT); Eric Rodenberg (Esri)
      # Contact:     kgerrow@esri.com; mmccart@hntb.com; hunter.praska@iowa.dot.gov; erodenberg@esri.com
      #
      # Created:     11/18/2015
      # Modified:    8/10/2016 - To include Feature Collection Creation on AGOL (Mark and Eric)
      #-------------------------------------------------------------------------------

      def getToken(adminUser, pw):
              data = {'username': adminUser,
                  'password': pw,
                  'referer' : 'https://www.arcgis.com',
                  'f': 'json'}
              url  = 'https://arcgis.com/sharing/rest/generateToken'
              jres = requests.post(url, data=data, verify=False).json()
              return jres['token'],jres['ssl']

      #generates account information
      def GetAccount(pref, tokenfun):
          URL= pref+'www.arcgis.com/sharing/rest/portals/self?f=json&token=' + tokenfun
          response = requests.get(URL, verify=False)
          jres = json.loads(response.text)
          return jres['urlKey']


      import requests, json
      # Next 3 lines of code are required to copy/create Feature Collections on AGOL
      import sys
      sys.path.append(r"C:\TEMP\OverwriteScript") #Originally provied by Eric R. at Esri, but not needed to run in FME
      from overwrite_RC_NonIA import run #Rename 'overwrite_AVL_Direct' to name of .py file you want to run. Store it here: C:\apps\FME\2016\python\python27\ for FME Desktop. For FME Server: Load to RESOURCES>ENGINE>PLUGINS>PYTHON via Web UI

      #Enter Username and Password
      user= "USERNAME" #raw_input('What is the ArcGIS Online Username?')
      pw = "PASSWORD" #raw_input('What is the ArcGIS Online Password?')

      #get account information
      token= getToken(user, pw)
      if token[1] == False:
                 pref='http://'
      else:
                 pref='https://'
      #Create Portal URL
      t=GetAccount(pref,token[0])
      portalUrl=pref+t


      restURL='http://services.arcgis.com/8lRhdTsQyJpO52F1/arcgis/rest/admin/services/MidwestWinterRoadConditions/FeatureServer/updateDefinition' #modify URL
      defCapabilities= '{"capabilities":"Query,Extract"}' #editing disabled
      data = {'updateDefinition': defCapabilities,
                  'token':token[0],
                  'f': 'json'}

      #Send Request
      res =requests.post(restURL, data = data, verify=False).json()
      print res
      if res['success']==True:
          print 'Service successfully Added'
      else:
          print 'Service NOT ADDED'

      # Run the Feature Collection creation script provided by Esri and modified for each FC
      config_file = r"C:\Apps\FME\2016\python\python27\overwrite_RC_NonIA.cfg" #For FME Desktop Only. Must copy .cfg and .py file here
      #config_file = r"C:\ProgramData\Safe Software\FME Server\resources\engine\Plugins\python\overwrite_RC_NonIA.cfg" #For FME Server Only. Must load to FME Server Resources
      run(config_file)

Parameters:
- SourceDataset_JSON = ""$(FME_MF_DIR)Data\Illinois.json" "$(FME_MF_DIR)Data\Kansas.json" "$(FME_MF_DIR)Data\Minnesota.json" "$(FME_MF_DIR)Data\Missouri.json" "$(FME_MF_DIR)Data\Nebraska.json" "$(FME_MF_DIR)Data\NorthDakota.json" "$(FME_MF_DIR)Data\SouthDakota.json" "$(FME_MF_DIR)Data\Wisconsin.json""   # Source JSON (JavaScript Object Notation) File or URL
- UTC_Offset = 6   # UTC Offset

Readers:
- JSON_1: JSON from $(SourceDataset_JSON)

Writers:
- ARCGISONLINEFEATURES_1: ARCGISONLINEFEATURES in SPHERICAL_MERCATOR

Note: Write to AGOL
RoadConditions (writer ARCGISONLINEFEATURES_1)
    attributes: OBJECTID esriFieldTypeInteger, HEADLINE esriFieldTypeString(2048), REPORT_UPDATED esriFieldTypeDate, REPORT_CREATED esriFieldTypeDate, DESCRIPTION esriFieldTypeString(2048), SOURCE esriFieldTypeString(2048), SOURCE_LINK esriFieldTypeString(2048), FMEDATA_READ esriFieldTypeDate, STATUS esriFieldTypeString(2048), REPORT_ID esriFieldTypeString(2048), AGOL_WRITE esriFieldTypeDate, ROAD_CONDITION esriFieldTypeSmallInteger

Bookmark: Read in JSON files
Illinois (reader JSON_1)
    attributes: SEGMENT_ID string, HEADLINE string, ROAD_CONDITION string, SEGMENT_NAME string, DESCRIPTION string, ROUTE_NAME string, REPORT_CREATED string, FMEDATA_READ string, STATUS string, SOURCE string, SOURCE_LINK string, REPORT_UPDATED string, OBJECTID int, PRIMARYMP string, SECONDARYMP string
    -> Road_Condition
Wisconsin (reader JSON_1)
    attributes: HEADLINE string, ROAD_CONDITION string, SEGMENT_NAME string, SEGMENT_ID string, PRIMARYMP string, SECONDARYMP string, ROUTE_NAME string, DESCRIPTION string, FMEDATA_READ string, STATUS string, OBJECTID int, SOURCE string, SOURCE_LINK string
    -> Road_Condition
SouthDakota (reader JSON_1)
    attributes: REPORT_CREATED string, PRIMARYMP string, SECONDARYMP string, DESCRIPTION string, HEADLINE string, ROAD_CONDITION string, FMEDATA_READ string, REPORT_UPDATED string, SEGMENT_ID string, SEGMENT_NAME string, ROUTE_NAME string, SOURCE_LINK string, SOURCE string, OBJECTID int
    -> Road_Condition
NorthDakota (reader JSON_1)
    attributes: SEGMENT_ID string, ROAD_CONDITION string, HEADLINE string, ROUTE_NAME string, DESCRIPTION string, PRIMARYMP string, SECONDARYMP string, SEGMENT_NAME string, REPORT_CREATED string, FMEDATA_READ string, REPORT_UPDATED string, SOURCE string, SOURCE_LINK string, STATUS string, OBJECTID int
    -> Road_Condition
Minnesota (reader JSON_1)
    attributes: ROAD_CONDITION string, SOURCE_LINK string, PRIMARYMP string, SECONDARYMP string, ROUTE_NAME string, SEGMENT_NAME string, SEGMENT_ID string, SEGMENT_OID string, PRIMARYLAT string, PRIMARYLONG string, SECONDARYLAT string, SECONDARYLONG string, REPORT_UPDATED string, REPORT_CREATED string, REPORT_ID string, HEADLINE string, DESCRIPTION string, FMEDATA_READ string, STATUS string, SOURCE string, OBJECTID int
    -> Road_Condition
Kansas (reader JSON_1)
    attributes: DESCRIPTION string, HEADLINE string, ROUTE_NAME string, SEGMENT_NAME string, PRIMARYMP string, SECONDARYMP string, ROAD_CONDITION string, REPORT_CREATED string, STATUS string, FMEDATA_READ string, SOURCE string, SOURCE_LINK string, REPORT_UPDATED string, OBJECTID string
    -> Road_Condition
Nebraska (reader JSON_1)
    attributes: ROAD_CONDITION string, SOURCE string, SOURCE_LINK string, PRIMARYMP string, SECONDARYMP string, ROUTE_NAME string, SEGMENT_NAME string, SEGMENT_ID string, SEGMENT_OID string, PRIMARYLAT string, PRIMARYLONG string, SECONDARYLAT string, SECONDARYLONG string, REPORT_UPDATED string, REPORT_CREATED string, REPORT_ID string, HEADLINE string, DESCRIPTION string, FMEDATA_READ string, STATUS string, SEGMENT_DATE string, OBJECTID int
    -> Road_Condition
Missouri (reader JSON_1) [off]
    attributes: DESCRIPTION string, ROAD_CONDITION string, HEADLINE string, SEGMENT_NAME string, PRIMARYMP string, SECONDARYMP string, ROUTE_NAME string, SEGMENT_ID string, STATUS string, FMEDATA_READ string, SOURCE string, SOURCE_LINK string, OBJECTID int
    -> Road_Condition

Bookmark: Final formatting
Note: Map Road Condition values / to domains
Road_Condition: AttributeValueMapper
    VAL_ATTR = ROAD_CONDITION
    DIRECTION = Forward (Source To Destination)
    DEFAULT_VALUE = 0
    SRC = ROAD_CONDITION
    LUT = Data Not Available,0,Seasonal,1,Partially Covered,2,Completely Covered,3,Travel Not Advised,4,Impassable,5
    -> StringCaseChanger
StringCaseChanger
    ATTRLIST = DESCRIPTION HEADLINE
    ATTRCHOICE = Selected Attributes
    CHANGE_TYPE = Full Title Case
    -> TimeStamper
Note: Time Stamp for write to AGOL
TimeStamper: AttributeManager
    ATTR_TABLE:
      SET_TO FMEDATA_READ = @DateTimeAdd(@Value(FMEDATA_READ),PT@Left(@Right(@DateTimeNow(local),4),1)H)
      SET_TO AGOL_WRITE = @Left(@DateTimeNow(utc),14)
    -> RoadConditions (writer ARCGISONLINEFEATURES_1)
