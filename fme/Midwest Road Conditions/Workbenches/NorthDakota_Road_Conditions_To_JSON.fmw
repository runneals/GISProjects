FME workspace NorthDakota_Road_Conditions_To_JSON.fmw
Title: North Dakota Road Conditions to GeoJSON
Description: This workspace reads data in from the North Dakota Winter Road Conditions Feature Services, merges it with the AGOL segment object ID, and writes it out to a json file.

Parameters:
- SourceDataset_ARCGISFEATURES_5 = http://gis.dot.nd.gov/arcgis/rest/services/external/rcrs_dynamic/MapServer   # Host
- SourceDataset_JSON = $(FME_MF_DIR)Segment\NorthDakota.json   # Source JSON (JavaScript Object Notation) File or URL
- DestDataset_JSON = $(FME_MF_DIR)Data\NorthDakota.json   # Destination JSON (JavaScript Object Notation) File

Readers:
- JSON_1: JSON from $(SourceDataset_JSON)
- ARCGISFEATURES_1: ARCGISFEATURES from $(SourceDataset_ARCGISFEATURES_5)

Writers:
- JSON_2: JSON to $(DestDataset_JSON)

Note: Date/Time Format / Attribute Standardization
Formatter: AttributeManager
    ATTR_TABLE:
      SET_TO FMEDATA_READ = @DateTimeAdd(@Timestamp(^Y^m^d^H^M^S),PT@Left(@Right(@DateTimeNow(local),4),1)H)
      SET_TO validatedtime = @DateTimeDiff(@Value(EditTime),@Value(FMEDATA_READ),Days)
      SET_TO SEGMENT_ID = @Value(Direction)@Value(ObjectID)
      SET_TO ROAD_CONDITION = FME_CONDITIONAL:DEFAULT_VALUE'Data Not Available'BOOL_OP;OR;COMPOSITE_TEST;<Unused>;TEST @Value(ConditionCategory) = Red;TEST @Value(CondDesc) = Closed;TEST @Value(CondDesc) = Road Blocked'Impassable'BOOL_OP;OR;COMPOSITE_TEST;<Unused>;TEST @Value(ConditionCategory) = RedWhite;TEST @Value(CondDesc) = No Travel Advised'Travel Not Advised'BOOL_OP;AND;COMPOSITE_TEST;<Unused>;TEST @Value(CondQual) = Scattered'Partially Covered'BOOL_OP;COMPOSITE;COMPOSITE_TEST;1 OR (2 AND 3);TEST @Value(ConditionCategory) = Green;TEST @Value(ConditionCategory) = Blue;TEST @Value(CondDesc) = Wet'Seasonal'BOOL_OP;OR;COMPOSITE_TEST;<Unused>;TEST @Value(ConditionCategory) = Yellow;TEST @Value(ConditionCategory) = Purple;TEST @Value(ConditionCategory) = Blue;TEST @Value(ConditionCategory) = LtBlue'Completely Covered'FME_NUM_CONDITIONS6___
      SET_TO HEADLINE = FME_CONDITIONAL:DEFAULT_VALUE'Data Not Available'BOOL_OP;OR;COMPOSITE_TEST;<Unused>;TEST @Value(ConditionCategory) = Red;TEST @Value(CondDesc) = Closed;TEST @Value(CondDesc) = Road Blocked'Impassable'BOOL_OP;OR;COMPOSITE_TEST;<Unused>;TEST @Value(ConditionCategory) = RedWhite;TEST @Value(CondDesc) = No Travel Advised'Travel Not Advised'BOOL_OP;AND;COMPOSITE_TEST;<Unused>;TEST @Value(ConditionCategory) = Blue;TEST @Value(CondQual) = Scattered'Partially Covered with Slush'BOOL_OP;AND;COMPOSITE_TEST;<Unused>;TEST @Value(ConditionCategory) = Purple;TEST @Value(CondQual) = Scattered'Partially Covered with Snow'BOOL_OP;AND;COMPOSITE_TEST;<Unused>;TEST @Value(ConditionCategory) = Yellow;TEST @Value(CondQual) = Scattered'Partially Covered with Ice'BOOL_OP;AND;COMPOSITE_TEST;<Unused>;TEST @Value(ConditionCategory) = LtBlue;TEST @Value(CondQual) = Scattered'Partially Covered with Frost'BOOL_OP;AND;COMPOSITE_TEST;<Unused>;TEST @Value(ConditionCategory) = Blue;TEST @Value(CondDesc) = Wet'Wet'BOOL_OP;OR;COMPOSITE_TEST;<Unused>;TEST @Value(ConditionCategory) = Green'Seasonal'BOOL_OP;OR;COMPOSITE_TEST;<Unused>;TEST @Value(ConditionCategory) = Yellow'Completely Covered with Ice'BOOL_OP;OR;COMPOSITE_TEST;<Unused>;TEST @Value(ConditionCategory) = Purple'Completely Covered with Snow'BOOL_OP;OR;COMPOSITE_TEST;<Unused>;TEST @Value(ConditionCategory) = Blue'Completely Covered with Slush'BOOL_OP;OR;COMPOSITE_TEST;<Unused>;TEST @Value(ConditionCategory) = LtBlue'Completely Covered with Frost'FME_NUM_CONDITIONS13___
      SET_TO visi = FME_CONDITIONAL:DEFAULT_VALUE'_FME_NO_OP_'BOOL_OP;OR;COMPOSITE_TEST;<Unused>;TEST VisiDesc NOT_ATTRIBUTE_VALUE_NULL _FME_BLANK_STRING_' // Visibility: @Value(VisiDesc)'FME_NUM_CONDITIONS2___
      SET_TO precip = FME_CONDITIONAL:DEFAULT_VALUE'_FME_NO_OP_'BOOL_OP;OR;COMPOSITE_TEST;<Unused>;TEST PrecipDesc NOT_ATTRIBUTE_VALUE_NULL _FME_BLANK_STRING_' // Precipitation: @Value(CondDesc)'FME_NUM_CONDITIONS2___
      SET_TO cond = FME_CONDITIONAL:DEFAULT_VALUE'@Value(CondDesc)'BOOL_OP;AND;COMPOSITE_TEST;<Unused>;TEST @Value(CondDesc) NOT_= Seasonal Conditions;TEST @Value(CondQual) NOT_= None'@Value(CondQual) @Value(CondDesc)'FME_NUM_CONDITIONS2___
      SET_TO ROUTE_NAME = @Value(HwyDesc) @Value(Direction)
      SET_TO DESCRIPTION = @Value(cond) // Travel Speeds: @Value(TravelSpeeds)@Value(precip)@Value(visi)
      REMOVE HwyDesc
      RENAME_SET_VALUE MPFrom > PRIMARYMP
      RENAME_SET_VALUE MPTo > SECONDARYMP
      RENAME_SET_VALUE SegmentName > SEGMENT_NAME
      REMOVE CondDesc
      REMOVE CondQual
      REMOVE VisiDesc
      REMOVE PrecipDesc
      REMOVE TravelSpeeds
      REMOVE Comment
      REMOVE Direction
      REMOVE ConditionCategory
      SET_TO REPORT_CREATED = @DateTimeAdd(@Value(EditTime),PT@Left(@Right(@DateTimeNow(local),4),1)H)
      SET_TO REPORT_UPDATED = @Value(REPORT_CREATED)
      SET_TO SOURCE = North Dakota DOT
      SET_TO SOURCE_LINK = http://www.dot.nd.gov/travel-info-v2/
      SET_TO STATUS = FME_CONDITIONAL:DEFAULT_VALUE'ACTIVE-CURRENT'BOOL_OP;OR;COMPOSITE_TEST;<Unused>;TEST @Value(validatedtime) <= -2'ACTIVE-STALE'FME_NUM_CONDITIONS2___
      REMOVE ObjectID
      REMOVE EditTime
    -> SEGMENT_ID [REQUESTOR]
Note: North Dakota Segment Geometry / with AGOL Objects IDs
NorthDakota (reader JSON_1)
    attributes: SEGMENT_ID string, ROUTE_NAME string, PRIMARYMP string, SECONDARYMP string, SEGMENT_NAME string, SOURCE string, SOURCE_LINK string, OBJECTID int, json_ogc_wkt_crs string, json_geometry object
    -> SEGMENT_ID [SUPPLIER]
Note: Merge Segment_ID
SEGMENT_ID: FeatureMerger
    JOIN_KEYS = @Value(SEGMENT_ID) @Value(SEGMENT_ID) AUTO
    ATTR_CONFLICT_RES = Use Requestor
    SUPPLIERS_FIRST = Yes
    MERGE_TYPE = Attributes Only
    IGNORE_NULLS = No
    ATTR_ACCUM_MODE = Merge Supplier
    REJECT_NULL_MISSING_KEYS = No
    PROCESS_DUPS = No
    MERGED -> NorthDakota (writer JSON_2)
Note: Write out to JSON File
NorthDakota (writer JSON_2)
    attributes: SEGMENT_ID string, ROAD_CONDITION string, HEADLINE string, ROUTE_NAME string, DESCRIPTION string, PRIMARYMP string, SECONDARYMP string, SEGMENT_NAME string, REPORT_CREATED string, FMEDATA_READ string, REPORT_UPDATED string, SOURCE string, SOURCE_LINK string, STATUS string, OBJECTID int

Bookmark: ND Road Conditions Feature Services
Road Conditions Conditions-N,E (reader ARCGISFEATURES_1)
    attributes: HwyDesc esriFieldTypeString(25), MPFrom esriFieldTypeSingle, MPTo esriFieldTypeSingle, SegmentName esriFieldTypeString(65), CondDesc esriFieldTypeString(50), CondQual esriFieldTypeString(25), VisiDesc esriFieldTypeString(25), PrecipDesc esriFieldTypeString(25), TravelSpeeds esriFieldTypeString(25), Comment esriFieldTypeString(50), Direction esriFieldTypeString(1), ConditionCategory esriFieldTypeString(25), EditTime esriFieldTypeDate, HwyName esriFieldTypeString(14), PublicFrom esriFieldTypeString(50), PublicTo esriFieldTypeString(50), MPCenter esriFieldTypeSingle, ConditionDesc esriFieldTypeString(50), CondExtent esriFieldTypeString(25), CondSecDesc esriFieldTypeString(50), CondSecQual esriFieldTypeString(25), CondSecExtent esriFieldTypeString(25), VisiQual esriFieldTypeString(25), VisiExtent esriFieldTypeString(25), VisiDensityDesc esriFieldTypeString(25), PrecipQual esriFieldTypeString(25), EffectiveUntil esriFieldTypeDate, ModifyTime esriFieldTypeDate, ObjectID esriFieldTypeOID, HwyNum esriFieldTypeSmallInteger,
      HwySuffix esriFieldTypeString(14), Type esriFieldTypeString(1), VisibilityDesc esriFieldTypeString(25), VisibilityDensityDesc esriFieldTypeString(25)
    -> Formatter
Road Conditions Conditions-S,W (reader ARCGISFEATURES_1)
    attributes: HwyDesc esriFieldTypeString(25), MPFrom esriFieldTypeSingle, MPTo esriFieldTypeSingle, SegmentName esriFieldTypeString(65), CondDesc esriFieldTypeString(50), CondQual esriFieldTypeString(25), VisiDesc esriFieldTypeString(25), PrecipDesc esriFieldTypeString(25), TravelSpeeds esriFieldTypeString(25), Comment esriFieldTypeString(50), Direction esriFieldTypeString(1), ConditionCategory esriFieldTypeString(25), EditTime esriFieldTypeDate, HwyName esriFieldTypeString(14), PublicFrom esriFieldTypeString(50), PublicTo esriFieldTypeString(50), MPCenter esriFieldTypeSingle, ConditionDesc esriFieldTypeString(50), CondExtent esriFieldTypeString(25), CondSecDesc esriFieldTypeString(50), CondSecQual esriFieldTypeString(25), CondSecExtent esriFieldTypeString(25), VisiQual esriFieldTypeString(25), VisiExtent esriFieldTypeString(25), VisiDensityDesc esriFieldTypeString(25), PrecipQual esriFieldTypeString(25), EffectiveUntil esriFieldTypeDate, ModifyTime esriFieldTypeDate, ObjectID esriFieldTypeOID, HwyNum esriFieldTypeSmallInteger,
      HwySuffix esriFieldTypeString(14), Type esriFieldTypeString(1), VisibilityDesc esriFieldTypeString(25), VisibilityDensityDesc esriFieldTypeString(25)
    -> Formatter
