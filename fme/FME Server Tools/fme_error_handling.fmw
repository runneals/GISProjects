FME workspace fme_error_handling.fmw
Title: Clean Error Notifications
Description: Help to prioritize errors and explain what they mean before emailing them off.
History: 9/20/2018,DR,First Beta Version,20200217,DR,Cleaned up for public release

Parameters:
- JSON = $(FME_TOPIC_MESSAGE)   # Source JSON (JavaScript Object Notation) File or URL
- Email =
- DestDataset_SQLITE3 = E:\Error Logs\errors.sqlite   # SQLite Database
- SMTP = SMTP   # Host
- FME_Server_Connection =   # "FME Server"% Connection

Readers:
- JSON_1: JSON from $(JSON)

Writers:
- SQLITE3_1: SQLITE3 to $(DestDataset_SQLITE3)

Note: IMPORTANT: / When setting up FME Server subscriptions to use this workspace, Check the box "Get Value from Topic Message" next to the Source JSON.
Note: Get JSON from notification
JSONFeature (reader JSON_1)
    attributes: workspace string, timeRequested string, requestKeyword string, timeStarted string, repository string, LogFileName string, StatusMessage string, jobfailure_topic string, StatusNumber int, id int, timeFinished string, logHome string, logUrl string
    -> FMEServerLogFileRetriever
FMEServerLogFileRetriever
    JOB_ID_VAL = @Value(id)
    LOG_ATTR = _log_attr
    SERVER_CONNECTION = $(FME_Server_Connection)
    -> NewPythonVersionErrorRemoval
NewPythonVersionErrorRemoval: StringReplacer
    CASE = NO
    FIND_TEXT = |ERROR |C:\Program Files\FMEServer\Server\fme\/python\urllib3\connectionpool.py:858: InsecureRequestWarning: Unverified HTTPS request is being made. Adding certificate verification is strongly advised. See: https://urllib3.readthedocs.io/en/latest/advanced-usage.html#ssl-warnings
    NO_MATCH = _FME_NO_OP_
    REGEXP = NO
    SRC_ATTRS = _log_attr
    -> StringReplacer
StringReplacer
    CASE = YES
    NO_MATCH = _FME_NO_OP_
    REGEXP = NO
    REPLACE_TEXT = "\n"
    SRC_ATTRS = _log_attr
    -> SearchError
SearchError: StringSearcher
    CASE = yes
    MATCHED_RESULT_ATTR = match
    MATCHES_ATTR = allmatch
    REGEXP = ERROR (.*)
    STRING_TO_SEARCH = @Value(_log_attr)
    MATCHED -> AttributeSplitter_2
    NOT_MATCHED -> TestFilter_2
    NOT_MATCHED -> Logs (writer SQLITE3_1)
    NOT_MATCHED -> TestFilter
AttributeSplitter_2
    ATTR_NAME = allmatch{1}.match
    DELIMITER = "\n"
    DROP_EMPTY_PARTS = Yes
    LIST_NAME = _list
    TRIM_OPTION = Both
    -> AttributeManager_2
AttributeManager_2
    ATTR_TABLE:
      SET_TO StatusMessage = @Value(_list{0})  |
        @Value(StatusMessage)
    -> TestFilter_2
    -> Logs (writer SQLITE3_1)
    -> TestFilter
Note: Write Logs to sqlite db to easily keep track of errors longer than you keep all the logs for (also searchable)
Logs (writer SQLITE3_1)
    attributes: workspace text, timeRequested text, requestKeyword text, timeStarted text, repository text, LogFileName text, StatusMessage text, jobfailure_topic text, StatusNumber integer, id integer, timeFinished text, logHome text, logUrl text, _log_attr varchar(200), match varchar(200)
Note: Can Easily Filter by Repository
TestFilter_2 [off]
    DEFAULT_VALUE = <UNFILTERED>
    TEST_LIST:
      "BOOL_OP,COMPOSITE,COMPOSITE_TEST,""""""1 AND 2 AND 3 AND 4 AND 5"""""",TEST_CLAUSE,TEST @Value(repository) = Winter Operations
      NUM_TEST @DateTimeFormat(@DateTimeNow(),%H) NOT_RANGE [01,03]
      CASE_INSENSITIVE_TEST @Value(StatusMessage) NOT_CONTAINS ORA-01033: ORACLE initialization or shutdown in progress
      CASE_INSENSITIVE_TEST @Value(StatusMessage) NOT_CONTAINS ORA-12518: TNS:listener could not hand off client connection
      CASE_INSENSITIVE_TEST @Value(StatusMessage) NOT_CONTAINS ORA-01034: ORACLE not available",Winter Operations
    <UNFILTERED> -> Emailer_2
Note: Also send email/other notifications
Emailer_2 [off]
    ATTACHGROUP = No
    BODY:
      @Value(StatusMessage)<br />
      <br />
      More details: https://fmeserver.gov/fmeserver/#/job/@Value(id)/summary<br />
      <br />
      Time Requested: @Value(timeRequested)<br />
      Time Started: @Value(timeStarted)<br />
      Time Finished: @Value(timeFinished)
    FROM = fmeserver@fmeserver.gov
    SERVICE = Generic SMTP
    SMTP_CONNECTION = HOST;$(SMTP);PORT;25;ENCRYPTION;None;TIMEOUT;60;AUTHENTICATION;NO;USERNAME;<Unused>;PASSWORD;<Unused>;FME_CONTROLLER_QUERY_FILE;transformers/dependencies/emailer/Generic SMTP.fme
    SUBJECT = [FME Failed]: @Value(repository)/@Value(workspace)
    TO = $(Email)
Note: ... or by Error
TestFilter [off]
    DEFAULT_VALUE = <UNFILTERED>
    TEST_LIST:
      "BOOL_OP,COMPOSITE,COMPOSITE_TEST,""""""( 1 OR ( 2 AND 3 ) OR ( 4 AND 5 )) OR ( 6 OR ( 7 AND 8 ) OR ( 9 AND 10 ) OR ( 11 AND 12 ))"""""",TEST_CLAUSE,CASE_INSENSITIVE_TEST @Value(StatusMessage) CONTAINS Python Exception : 500 Server Error: Internal Server Error for url: https://services.arcgis.com
      CASE_INSENSITIVE_TEST @Value(StatusMessage) CONTAINS ArcGIS Online Feature Service Writer: Could not access Feature Service at 'https://services.arcgis.com
      CASE_INSENSITIVE_TEST @Value(StatusMessage) CONTAINS This may be a temporary server issue, or insufficient permissions. The error code from the server was '500' and the message was: 'Unauthorized access'
      CASE_INSENSITIVE_TEST @Value(StatusMessage) CONTAINS ArcGIS Feature Service Reader: Could not access Feature Service at 'https://services.arcgis.com
      CASE_INSENSITIVE_TEST @Value(StatusMessage) CONTAINS This may be a temporary server issue, or insufficient permissions. The error code from the server was '500' and the message was: 'Unauthorized access'
      CASE_INSENSITIVE_TEST @Value(_log_attr) CONTAINS Python Exception : 500 Server Error: Internal Server Error for url: https://services.arcgis.com
      CASE_INSENSITIVE_TEST @Value(_log_attr) CONTAINS ArcGIS Online Feature Service Writer: Could not access Feature Service at 'https://services.arcgis.com
      CASE_INSENSITIVE_TEST @Value(_log_attr) CONTAINS This may be a temporary server issue, or insufficient permissions. The error code from the server was '500' and the message was: 'Unauthorized access'
      CASE_INSENSITIVE_TEST @Value(_log_attr) CONTAINS ArcGIS Feature Service Reader: Could not access Feature Service at 'https://services.arcgis.com
      CASE_INSENSITIVE_TEST @Value(_log_attr) CONTAINS This may be a temporary server issue, or insufficient permissions. The error code from the server was '500' and the message was: 'Unauthorized access'
      CASE_INSENSITIVE_TEST @Value(_log_attr) CONTAINS Could not access Feature Service at 'https://services
      CASE_INSENSITIVE_TEST @Value(_log_attr) CONTAINS This may be a temporary server issue, or insufficient permissions. The error code from the server was '500' and the message was: 'Unauthorized access'",AGO 500,"BOOL_OP,OR,COMPOSITE_TEST,""""""1 OR 2 OR 3 OR 4 OR 5 OR 6"""""",TEST_CLAUSE,CASE_INSENSITIVE_TEST @Value(StatusMessage) CONTAINS ArcGIS Online Feature Service Writer: Encountered an unexpected error. The error code from the server was '502' and the message was: 'An error occurred.'. Details: ''
      CASE_INSENSITIVE_TEST @Value(StatusMessage) CONTAINS ArcGIS Feature Service Reader: Encountered an unexpected error. The error code from the server was '502' and the message was: 'An error occurred.'. Details: ''
      CASE_INSENSITIVE_TEST @Value(StatusMessage) CONTAINS ArcGIS Online Feature Service Reader: Encountered an unexpected error. The error code from the server was '502' and the message was: 'An error occurred.'. Details: ''
      CASE_INSENSITIVE_TEST @Value(_log_attr) CONTAINS Python Exception <HTTPError>: 502 Server Error: Bad Gateway for url: https://www.arcgis.com
      CASE_INSENSITIVE_TEST @Value(_log_attr) CONTAINS ArcGIS Online Feature Service Writer: Encountered an unexpected error. The error code from the server was '502' and the message was: 'An error occurred.'. Details: ''
      CASE_INSENSITIVE_TEST @Value(_log_attr) CONTAINS ArcGIS Online Feature Service Reader: Encountered an unexpected error. The error code from the server was '502' and the message was: 'An error occurred.'. Details: ''",AGO 502,"BOOL_OP,OR,COMPOSITE_TEST,""""""<Unused>"""""",TEST_CLAUSE,CASE_INSENSITIVE_TEST @Value(StatusMessage) CONTAINS ArcGIS Online Feature Service Writer: Encountered an unexpected error. The error code from the server was '503' and the message was: 'An error occurred.'. Details: ''
      CASE_INSENSITIVE_TEST @Value(StatusMessage) CONTAINS ArcGIS Online Feature Service Reader: Encountered an unexpected error. The error code from the server was '503' and the message was: 'An error occurred.'. Details: ''
      CASE_INSENSITIVE_TEST @Value(StatusMessage) CONTAINS ArcGIS Feature Service Reader: Encountered an unexpected error. The error code from the server was '503' and the message was: 'An error occurred.'. Details: ''
      CASE_INSENSITIVE_TEST @Value(_log_attr) CONTAINS ArcGIS Online Feature Service Writer: Encountered an unexpected error. The error code from the server was '503' and the message was: 'An error occurred.'. Details: ''
      CASE_INSENSITIVE_TEST @Value(_log_attr) CONTAINS ArcGIS Online Feature Service Reader: Encountered an unexpected error. The error code from the server was '503' and the message was: 'An error occurred.'. Details: ''",AGO 503,"BOOL_OP,OR,COMPOSITE_TEST,""""""<Unused>"""""",TEST_CLAUSE,CASE_INSENSITIVE_TEST @Value(StatusMessage) CONTAINS ArcGIS Online Feature Service Writer: Encountered an unexpected error. The error code from the server was '504' and the message was: 'Your request has timed out.'. Details: ''
      CASE_INSENSITIVE_TEST @Value(StatusMessage) CONTAINS Python Exception : 504 Server Error: Gateway Time-out for url: https://www.arcgis.com/
      CASE_INSENSITIVE_TEST @Value(StatusMessage) CONTAINS ArcGIS Feature Service Reader: Encountered an unexpected error. The error code from the server was '504' and the message was: 'Your request has timed out.'. Details: ''
      CASE_INSENSITIVE_TEST @Value(_log_attr) CONTAINS ArcGIS Online Feature Service Writer: Encountered an unexpected error. The error code from the server was '504' and the message was: 'Your request has timed out.'. Details: ''
      CASE_INSENSITIVE_TEST @Value(_log_attr) CONTAINS Python Exception : 504 Server Error: Gateway Time-out for url: https://www.arcgis.com/
      CASE_INSENSITIVE_TEST @Value(_log_attr) CONTAINS ArcGIS Feature Service Reader: Encountered an unexpected error. The error code from the server was '504' and the message was: 'Your request has timed out.'. Details: ''",AGO 504,"BOOL_OP,OR,COMPOSITE_TEST,""""""1 OR 2"""""",TEST_CLAUSE,CASE_INSENSITIVE_TEST @Value(_log_attr) CONTAINS The error code from the server was '1000' and the message was: 'ExecuteScalar requires an open and available Connection. The connection's current state is closed.'
      CASE_INSENSITIVE_TEST @Value(_log_attr) CONTAINS The error code from the server was '1000' and the message was: 'A transport-level error has occurred when receiving results from the server. (provider: SSL Provider, error: 0 - The specified data could not be decrypted.",AGO 1000,"BOOL_OP,OR,COMPOSITE_TEST,""""""1 OR 2 OR 3 OR 4"""""",TEST_CLAUSE,CASE_INSENSITIVE_TEST @Value(_log_attr) CONTAINS Python Exception : 503 Server Error: Service Unavailable for url: https://services-nocdn.arcgis.com/
      CASE_INSENSITIVE_TEST @Value(StatusMessage) CONTAINS Python Exception : 503 Server Error: Service Unavailable for url: https://services-nocdn.arcgis.com/
      CASE_INSENSITIVE_TEST @Value(_log_attr) CONTAINS Python Exception : 503 Server Error: Service Unavailable for url: https://utility.arcgis.com/usrsvcs/servers/
      CASE_INSENSITIVE_TEST @Value(StatusMessage) CONTAINS Python Exception : 503 Server Error: Service Unavailable for url: https://utility.arcgis.com/usrsvcs/servers/",AGO 503 NEW,"BOOL_OP,AND,COMPOSITE_TEST,""""""1 AND 2"""""",TEST_CLAUSE,CASE_INSENSITIVE_TEST @Value(StatusMessage) CONTAINS message was:
      CASE_INSENSITIVE_TEST @Value(StatusMessage) CONTAINS ArcGIS Online Feature Service",AGO 503 NEW other
    AGO 500 -> FMEServerJobSubmitter
    AGO 502 -> FMEServerJobSubmitter
    AGO 503 -> FMEServerJobSubmitter
    AGO 504 -> FMEServerJobSubmitter
    AGO 1000 -> FMEServerJobSubmitter
    AGO 503 NEW -> FMEServerJobSubmitter
    AGO 503 NEW other -> FMEServerJobSubmitter
Note: Can easily re-run jobs that have failed with known or unknown errors
FMEServerJobSubmitter [off]
    BLOCKING = No
    PRIORITY = 1 (highest)
    PROCESSING_MODE = In Sequence
    REPOSITORY = @Value(repository)
    SERVER_CONNECTION = $(FME_Server_Connection)
    TM_TTL = 30
    WORKSPACE_NAME = @Value(workspace)
