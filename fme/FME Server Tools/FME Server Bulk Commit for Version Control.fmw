FME workspace FME Server Bulk Commit for Version Control.fmw
Title: Bulk Commit Items for Version Control
Description: This workspace is used to bulk commit items to version control. Also can enable auto push to remote repository!
Usage: Uses the undocumented versioncontrol REST services, so different versions may break this. Tested in 18547.
History: 2019/05/23,DR,First Version

Parameters:
- FMEToken =   # FME Token
- FMEServerURL =   # Server URL for FME Server

Bookmark: Get list of repositories
Creator
    GEOMTYPE = Geometry Object
    NUM = 1
    CREATED -> getRepositoriesList
getRepositoriesList: HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = $(FMEServerURL)/fmerest/v3/repositories?limit=-1&offset=-1&fmetoken=$(FMEToken)
    TRANSFER_TIMEOUT_LENGTH = 90
    USE_COOKIES = No
    VERIFY_SSL_CERTIFICATES = Yes
    -> JSONFlattener
JSONFlattener
    ERROR_LIST_ATTR = _json_error
    JSON_DOCUMENT = @Value(_response_body)
    NEW_ATTRIBUTES = items{} description name owner sharable
    READ_FROM_FILE = NO
    RECURSIVE = Yes
    -> ListExploder
ListExploder
    ATTR_ACCUM_MODE = Merge List Attributes
    ATTR_CONFLICT_RES = Use List Attribute Values
    INDEX_ATTR = _element_index
    LIST_ATTR = items{}
    ELEMENTS -> encodeRepositoryName
encodeRepositoryName: TextEncoder
    DEST_ATTR = encoded.repositoryName
    ENCODING_TYPE = URL_ENCODE
    STRING_TO_ENCODE = @Value(name)
    -> getItems

Bookmark: Get list of items in repositories
getItems: HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = $(FMEServerURL)/fmerest/v3/repositories/@Value(encoded.repositoryName)/items?fmetoken=$(FMEToken)
    TRANSFER_TIMEOUT_LENGTH = 90
    USE_COOKIES = No
    VERIFY_SSL_CERTIFICATES = Yes
    -> JSONFlattener_2
JSONFlattener_2
    ERROR_LIST_ATTR = _json_error
    JSON_DOCUMENT = @Value(_response_body)
    NEW_ATTRIBUTES = items{} lastSaveDate lastPublishDate name description repositoryName title type userName
    READ_FROM_FILE = NO
    RECURSIVE = Yes
    -> ListExploder_2
Note: Rejected repositories mean that there are no items in that repository
ListExploder_2
    ATTR_ACCUM_MODE = Merge List Attributes
    ATTR_CONFLICT_RES = Use List Attribute Values
    INDEX_ATTR = _element_index
    LIST_ATTR = items{}
    ELEMENTS -> encodeWorkspaceName
encodeWorkspaceName: TextEncoder
    DEST_ATTR = encoded.workspaceName
    ENCODING_TYPE = URL_ENCODE
    STRING_TO_ENCODE = @Value(name)
    -> encodeCommitMessage

Bookmark: Commit all items to local repo
encodeCommitMessage: TextEncoder
    DEST_ATTR = encoded.commitMessage
    ENCODING_TYPE = URL_ENCODE
    STRING_TO_ENCODE = Auto Commit | Workspace Last Saved: @Value(lastSaveDate) | Workspace Last Published: @Value(lastPublishDate)
    -> postCommit
postCommit: HTTPCaller
    CONNECTION_TIMEOUT_LENGTH = 60
    CUSTOM_HEADERS = Content-Type;application/x-www-form-urlencoded Accept;application/json, text/plain, */* Authorization;fmetoken token=$(FMEToken)
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = $(FMEServerURL)/fmerest/v3/versioncontrol/local/commit/@Value(encoded.repositoryName)/@Value(encoded.workspaceName)
    TRANSFER_TIMEOUT_LENGTH = 90
    UPLOAD_BODY = commitMessage=@Value(encoded.commitMessage)&itemName=@Value(encoded.workspaceName)
    UPLOAD_CONTENT_TYPE = URL Encoded (application/x-www-form-urlencoded)
    UPLOAD_TYPE = Specify Upload Body
    USE_COOKIES = No
    VERIFY_SSL_CERTIFICATES = Yes
    -> StatisticsCalculator
    <REJECTED> -> commit_errors
Note: 409 error means that the item hasn't been changed since it was last committed
commit_errors: Inspector [off]

Bookmark: Push local repo to remote... Don't enable unless you're sure you want to auto push!
StatisticsCalculator
    COMPUTE_HISTOGRAM = NO
    COUNT_ATTR = _count
    PREPEND_ATTR_NAME_CHOICE = For multiple results only
    STATS_ATTRS = name
    SUMMARY -> postRemotePush
postRemotePush: HTTPCaller
    CONNECTION_TIMEOUT_LENGTH = 60
    CUSTOM_HEADERS = Content-Type;application/x-www-form-urlencoded Accept;application/json Authorization;fmetoken token=$(FMEToken)
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = $(FMEServerURL)/fmerest/v3/versioncontrol/remote/push
    TRANSFER_TIMEOUT_LENGTH = 90
    UPLOAD_BODY = force=false
    UPLOAD_CONTENT_TYPE = URL Encoded (application/x-www-form-urlencoded)
    UPLOAD_TYPE = Specify Upload Body
    USE_COOKIES = No
    VERIFY_SSL_CERTIFICATES = Yes
