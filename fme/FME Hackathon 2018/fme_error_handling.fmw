FME workspace fme_error_handling.fmw
Title: Clean Error Notifications
Description: Help to prioritize errors and explain what they mean before emailing them off.
History: 11/30/2018,DR,First Beta Version

Parameters:
- FAILED_JSON = $(FME_TOPIC_MESSAGE)   # The $(FME_TOPIC_MESSAGE)
- FME_SERVER_CONNECTION = fmeserver   # "FME Server" Connection to read log files
- SAD_LOGS_DB = E:\Sad Logs\errors.sqlite   # SQLite Database
- TO_EMAIL_WORK =   # Work Email
- TO_EMAIL_PERSONAL =
- SMTP_SERVER = SMTP   # SMTP Server
- FROM_EMAIL = fmeserver@yourdomain.gov   # From Email
- FME_SERVER_URL = https://fme.yourcompany.com   # Base FME Server URL (ie https://fme.yourcompany.com)

Readers:
- JSON_1: JSON from $(FAILED_JSON)

Writers:
- SQLITE3_1: SQLITE3 to $(SAD_LOGS_DB)

Note: This needs to be set up as a subscription and subscribed to topics that are associated with failed jobs. / Action is required on your part for the annotations in RED. / Further notes... You can add further filtering rules for who it sends to and the message it sends (ie. sending an IT a message when the database has issues with the database error you're getting.... or including actions that need to be taken to get a job working again based on an error), but I just started this and I don't know all the errors, so I'll just send them all off :)
Note: This should be set up in your subscriptions as $(FME_TOPIC_MESSAGE) -- or just check the "Get Value from Topic Message" box
JSONFeature (reader JSON_1)
    attributes: workspace string, timeRequested string, requestKeyword string, timeStarted string, repository string, LogFileName string, StatusMessage string, jobfailure_topic string, StatusNumber int, id int, timeFinished string, logHome string, logUrl string
    -> FMEServerLogFileRetriever
Note: Retrieve Log File from server. NOTE this needs access to your server logs!
FMEServerLogFileRetriever
    JOB_ID_VAL = @Value(id)
    LOG_ATTR = _log_attr
    SERVER_CONNECTION = $(FME_SERVER_CONNECTION)
    -> NewPythonVersionErrorRemoval
Note: Remove that New Python error message... Because you should already know about that :)
NewPythonVersionErrorRemoval: StringReplacer
    CASE = NO
    FIND_TEXT = |ERROR |C:\Program Files\FMEServer\Server\fme\/python\urllib3\connectionpool.py:858: InsecureRequestWarning: Unverified HTTPS request is being made. Adding certificate verification is strongly advised. See: https://urllib3.readthedocs.io/en/latest/advanced-usage.html#ssl-warnings
    NO_MATCH = _FME_NO_OP_
    REGEXP = NO
    SRC_ATTRS = _log_attr
    -> StringReplacer
Note: Change Carriage Returns to New Lines
StringReplacer
    CASE = YES
    NO_MATCH = _FME_NO_OP_
    REGEXP = NO
    REPLACE_TEXT = "\n"
    SRC_ATTRS = _log_attr
    -> StringSearcher
Note: Create List of log lines that are marked as ERROR (Note, that the regex doesn't seem to work as documented, but I have done my best to work around that)
StringSearcher
    CASE = yes
    MATCHED_RESULT_ATTR = match
    MATCHES_ATTR = allmatch
    REGEXP = ^(.*)"|ERROR (.*)$^
    STRING_TO_SEARCH = @Value(_log_attr)
    MATCHED -> AttributeSplitter
    NOT_MATCHED -> TestFilter_2
    NOT_MATCHED -> Logs (writer SQLITE3_1)
Note: Keep all error logs in a db for later analysis
Logs (writer SQLITE3_1)
    attributes: workspace text, timeRequested text, requestKeyword text, timeStarted text, repository text, LogFileName text, StatusMessage text, jobfailure_topic text, StatusNumber integer, id integer, timeFinished text, logHome text, logUrl text, _log_attr varchar(200), match varchar(200)

Bookmark: If a list is created, parse the first error
AttributeSplitter
    ATTR_NAME = allmatch{1}.match
    DELIMITER = "\n"
    DROP_EMPTY_PARTS = Yes
    LIST_NAME = _list
    TRIM_OPTION = Both
    -> StatusMessage
StatusMessage: AttributeManager
    ATTR_TABLE:
      SET_TO StatusMessage = @Value(_list{0})  |
        @Value(StatusMessage)
    -> TestFilter_2
    -> Logs (writer SQLITE3_1)

Bookmark: Notifications
Note: Added filter to not send emails to personal emails when database goes down for backup. This should reduce the number of emails to personal emails.
TestFilter_2
    DEFAULT_VALUE = <UNFILTERED>
    TEST_LIST:
      "BOOL_OP,COMPOSITE,COMPOSITE_TEST,""""""1 AND (2 AND (3 OR 4 OR 5))"""""",TEST_CLAUSE,TEST @Value(repository) = Winter Operations
      NUM_TEST @DateTimeFormat(@DateTimeNow(),%H) RANGE [01,02]
      CASE_INSENSITIVE_TEST @Value(StatusMessage) CONTAINS ORA-01033: ORACLE initialization or shutdown in progress
      CASE_INSENSITIVE_TEST @Value(StatusMessage) CONTAINS ORA-12518: TNS:listener could not hand off client connection
      CASE_INSENSITIVE_TEST @Value(StatusMessage) CONTAINS ORA-01034: ORACLE not available",Winter Operations
    Winter Operations -> WinterOpsEmailer
    <UNFILTERED> -> WorkEmailer
WinterOpsEmailer: Emailer
    ATTACHGROUP = No
    BODY:
      @Value(StatusMessage)<br />
      <br />
      More details: $(FME_SERVER_URL)/fmeserver/#/job/@Value(id)/summary<br />
      <br />
      Time Requested: @Value(timeRequested)<br />
      Time Started: @Value(timeStarted)<br />
      Time Finished: @Value(timeFinished)
    FROM = $(FROM_EMAIL)
    SERVICE = Generic SMTP
    SMTP_CONNECTION = HOST;$(SMTP_SERVER);PORT;25;ENCRYPTION;None;TIMEOUT;60;AUTHENTICATION;NO;USERNAME;<Unused>;PASSWORD;<Unused>;FME_CONTROLLER_QUERY_FILE;transformers\dependencies\emailer\Generic SMTP.fme
    SUBJECT = [FME Failed]: @Value(repository)/@Value(workspace)
    TO = $(TO_EMAIL_WORK), $(TO_EMAIL_PERSONAL)
WorkEmailer: Emailer
    ATTACHGROUP = No
    BODY:
      @Value(StatusMessage)<br />
      <br />
      More details: $(FME_SERVER_URL)/fmeserver/#/job/@Value(id)/summary<br />
      <br />
      Time Requested: @Value(timeRequested)<br />
      Time Started: @Value(timeStarted)<br />
      Time Finished: @Value(timeFinished)
    FROM = $(FROM_EMAIL)
    SERVICE = Generic SMTP
    SMTP_CONNECTION = HOST;$(SMTP_SERVER);PORT;25;ENCRYPTION;None;TIMEOUT;60;AUTHENTICATION;NO;USERNAME;<Unused>;PASSWORD;<Unused>;FME_CONTROLLER_QUERY_FILE;transformers\dependencies\emailer\Generic SMTP.fme
    SUBJECT = [FME Failed]: @Value(repository)/@Value(workspace)
    TO = $(TO_EMAIL_WORK)
