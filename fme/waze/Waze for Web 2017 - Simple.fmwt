FME workspace Waze for Web 2017 - Simple.fmwt
Title: Waze for Web 2017 - Simple
Description: This workspace reads in the Waze Connected Citizen Partner's XML feed, parses the feed to send notification emails, then writes records to a live table and historical table in Oracle. CSV files are also utilized to keep track of the UUIDs of notifications that have been sent via email. Note that this workflow is currently only designed to handle point based reports, and won't handle traffic jam data that is in the feed as a polyline.
Usage: If your agency is looking to gain access to the Waze feed, check out https://www.waze.com/ccp
For more information, contact Eric Abrams or David Runneals
History: 5/2015,David Runneals,Created Workflow,7/15/2015,David Runneals,Added Alert Emailer,7/28/2015,Hunter Praska,Updated Alert Emailer,9/9/2015,David Runneals,Created TOC Emailer & Further Email Filtering Rules,9/30/2015,David Runneals,Added IMGURL to python script, emails, and database,10/13/2015,David Runneals,Added Historical Waze Database,10/26/2015,David Runneals,Created Highway Helper Filter & Emailer,11/10/2015,David Runneals,Added additional filter to rerun events along 80/35 in Des Moines + events that initially don't pick up a mp using GetBestRouteBySysRouteId,4/17/2017,David Runneals,Cleaned up for publishing to the web

Parameters:
- WAZE_XML_Feed = $(FME_MF_DIR)sampledata_waze.xml   # Waze XML Feed
- FILEGDB = $(FME_MF_DIR)Waze.gdb   # File Geodatabase

Readers:
- FILEGDB_1: FILEGDB from $(FILEGDB)
- XML_1: XML from $(WAZE_XML_Feed)

Writers:
- FILEGDB_2: FILEGDB to $(FILEGDB)

Feature (reader XML_1)
    attributes: BLOCKINGALERTUUID xml_char(37), CITY xml_char(19), COUNTRY xml_char(3), DELAY xml_decimal(4,0), DESCRIPTION xml_char(61), ENDNODE xml_char(19), IMAGEURL xml_char(74), LENGTH xml_decimal(5,0), LEVEL xml_decimal(2,0), MAGVAR xml_decimal(4,0), RELIABILITY xml_decimal(3,0), REPORTRATING xml_decimal(2,0), ROADTYPE xml_decimal(3,0), SPEED xml_decimal(18,15), STARTNODE xml_char(12), STREET xml_char(40), SUBTYPE xml_char(31), TURNTYPE xml_char(5), TYPE xml_char(14), UUID xml_char(37), XYLINE xml_char(895), XYPOINT xml_char(38), pubDate xml_char(31)
    -> TimeStamper
TimeStamper
    FMT = ^Y^m^dT^H^M^S
    TIME_ATTR = DATETIME
    -> AttributeSplitter
AttributeSplitter
    TRIM_OPTION = Both
    DELIMITER = " "
    ATTR_NAME = XYPOINT
    DROP_EMPTY_PARTS = No
    LIST_NAME = XYPOINT
    -> AttributeCreator_2
Note: Successfully got LRS Location & on state road network
Note: Not on state road network
AttributeCreator_2
    ATTR_TABLE:
      SET_TO LONG = @Value(XYPOINT{1})
      SET_TO LAT = @Value(XYPOINT{0})
    -> VertexCreator
AttributeCreator
    ATTR_TABLE:
      SET_TO ICON_RELIABILITY = FME_CONDITIONAL:DEFAULT_VALUE'_FME_NO_OP_'BOOL_OP;OR;COMPOSITE_TEST;<Unused>;TEST @Value(RELIABILITY) = 0;TEST @Value(RELIABILITY) = 1;TEST @Value(RELIABILITY) = 2;TEST @Value(RELIABILITY) = 3'@Value(STREET_TYPE)L'BOOL_OP;OR;COMPOSITE_TEST;<Unused>;TEST @Value(RELIABILITY) = 4;TEST @Value(RELIABILITY) = 5;TEST @Value(RELIABILITY) = 6'@Value(STREET_TYPE)M'BOOL_OP;OR;COMPOSITE_TEST;<Unused>;TEST @Value(RELIABILITY) = 7;TEST @Value(RELIABILITY) = 8;TEST @Value(RELIABILITY) = 9;TEST @Value(RELIABILITY) = 10'@Value(STREET_TYPE)H'FME_NUM_CONDITIONS4___
      SET_TO LATITUDE = @Value(LAT)
      SET_TO LONGITUDE = @Value(LONG)
    -> AttributeFilter_2
AttributeFilter_2
    ATTR_VALUES = <EMPTY>,<MISSING>,<NULL>,<UNFILTERED>,HAZARD_ON_ROAD,HAZARD_ON_SHOULDER,HAZARD_WEATHER,HAZARD_ON_ROAD_OBJECT,HAZARD_ON_ROAD_POT_HOLE,HAZARD_ON_ROAD_ROAD_KILL,HAZARD_ON_SHOULDER_CAR_STOPPED,HAZARD_ON_SHOULDER_MISSING_SIGN,HAZARD_ON_SHOULDER_ANIMALS,HAZARD_WEATHER_FOG,HAZARD_WEATHER_HAIL,HAZARD_WEATHER_HEAVY_RAIN,HAZARD_WEATHER_HEAVY_SNOW,HAZARD_WEATHER_FLOOD,HAZARD_WEATHER_MONSOON,HAZARD_WEATHER_TORNADO,HAZARD_WEATHER_HEAT_WAVE,HAZARD_WEATHER_HURRICANE,HAZARD_WEATHER_FREEZING_RAIN,HAZARD_ON_ROAD_LANE_CLOSED,HAZARD_ON_ROAD_OIL,HAZARD_ON_ROAD_ICE,HAZARD_ON_ROAD_CONSTRUCTION,HAZARD_ON_ROAD_CAR_STOPPED,ROAD_CLOSED_HAZARD,ROAD_CLOSED_CONSTRUCTION,ROAD_CLOSED_EVENT,JAM_LIGHT_TRAFFIC,JAM_STAND_STILL_TRAFFIC,JAM_HEAVY_TRAFFIC,JAM_MODERATE_TRAFFIC,ACCIDENT_MAJOR,ACCIDENT_MINOR,POLICE_HIDING,POLICE_VISIBLE
    ATTR_NAME = SUBTYPE
    <UNFILTERED> -> AttributeFilter_4
    HAZARD_ON_ROAD -> warning
    HAZARD_ON_SHOULDER -> warning
    HAZARD_WEATHER -> weather_hazard
    HAZARD_ON_ROAD_OBJECT -> info
    HAZARD_ON_ROAD_POT_HOLE -> info
    HAZARD_ON_ROAD_ROAD_KILL -> warning
    HAZARD_ON_SHOULDER_CAR_STOPPED -> warning
    HAZARD_ON_SHOULDER_MISSING_SIGN -> info
    HAZARD_ON_SHOULDER_ANIMALS -> warning
    HAZARD_WEATHER_FOG -> weather_hazard
    HAZARD_WEATHER_HAIL -> weather_hazard
    HAZARD_WEATHER_HEAVY_RAIN -> weather_hazard
    HAZARD_WEATHER_HEAVY_SNOW -> weather_hazard
    HAZARD_WEATHER_FLOOD -> weather_hazard
    HAZARD_WEATHER_MONSOON -> weather_hazard
    HAZARD_WEATHER_TORNADO -> weather_hazard
    HAZARD_WEATHER_HEAT_WAVE -> weather_hazard
    HAZARD_WEATHER_HURRICANE -> weather_hazard
    HAZARD_WEATHER_FREEZING_RAIN -> weather_hazard
    HAZARD_ON_ROAD_LANE_CLOSED -> lane_closure
    HAZARD_ON_ROAD_OIL -> warning
    HAZARD_ON_ROAD_ICE -> weather_hazard
    HAZARD_ON_ROAD_CONSTRUCTION -> construction
    HAZARD_ON_ROAD_CAR_STOPPED -> warning
    ROAD_CLOSED_HAZARD -> closure
    ROAD_CLOSED_CONSTRUCTION -> closure
    ROAD_CLOSED_EVENT -> closure
    JAM_LIGHT_TRAFFIC -> info
    JAM_STAND_STILL_TRAFFIC -> heavy_standstill_traffic
    JAM_HEAVY_TRAFFIC -> heavy_standstill_traffic
    JAM_MODERATE_TRAFFIC -> moderate_traffic
    ACCIDENT_MAJOR -> accident
    ACCIDENT_MINOR -> accident
    POLICE_VISIBLE -> info
AttributeFilter_4
    ATTR_VALUES = <EMPTY>,<MISSING>,<NULL>,<UNFILTERED>,ACCIDENT,ROAD_CLOSED,CONSTRUCTION,MISC
    ATTR_NAME = TYPE
    <UNFILTERED> -> warning
    ACCIDENT -> accident
    ROAD_CLOSED -> closure
    CONSTRUCTION -> construction
    MISC -> info
warning: AttributeCreator
    ATTR_TABLE = SET_TO ICON = warning
    -> Counter
info: AttributeCreator
    ATTR_TABLE = SET_TO ICON = info
    -> Counter
construction: AttributeCreator
    ATTR_TABLE = SET_TO ICON = construction
    -> Counter
closure: AttributeCreator
    ATTR_TABLE = SET_TO ICON = closure
    -> Counter
accident: AttributeCreator
    ATTR_TABLE = SET_TO ICON = accident
    -> Counter
weather_hazard: AttributeCreator
    ATTR_TABLE = SET_TO ICON = weather_hazard
    -> Counter
lane_closure: AttributeCreator
    ATTR_TABLE = SET_TO ICON = lane_closure
    -> Counter
heavy_standstill_traffic: AttributeCreator
    ATTR_TABLE = SET_TO ICON = heavy_standstill_traffic
    -> Counter
moderate_traffic: AttributeCreator
    ATTR_TABLE = SET_TO ICON = moderate_traffic
    -> Counter
Counter
    START = 1
    CNT_ATTR = OBJECTID
    SCOPE = Global
    DOMAIN = counter
    -> Live (writer FILEGDB_2)
Live (writer FILEGDB_2)
    attributes: ICON text(200), ICON_RELIABILITY text(200), LATITUDE text(200), LONGITUDE text(200), STREET_TYPE text(200), LONG text(200), LAT text(200), BLOCKINGALERTUUID text(37), CITY text(19), COUNTRY text(3), DELAY double, DESCRIPTION text(61), ENDNODE text(19), IMAGEURL text(74), LENGTH double, LEVEL double, MAGVAR double, RELIABILITY double, REPORTRATING double, ROADTYPE double, SPEED double, STARTNODE text(12), STREET text(40), SUBTYPE text(31), TURNTYPE text(5), TYPE text(14), UUID text(37), XYLINE text(895), XYPOINT text(38), pubDate text(31),
      DATETIME text(200), XYPOINT__ text(200), _matched_characters text(200), _matched_parts___part text(200), _matched_parts___startIndex text(200), OBJECTID text(200)
TimeStamper_2
    FMT = ^Y^m^dT^H^M^S
    TIME_ATTR = DATETIME
    -> AttributeCreator_6
AttributeCreator_6
    ATTR_TABLE:
      SET_TO ICON_RELIABILITY = FME_CONDITIONAL:DEFAULT_VALUE'_FME_NO_OP_'BOOL_OP;OR;COMPOSITE_TEST;<Unused>;TEST @Value(RELIABILITY) = 0;TEST @Value(RELIABILITY) = 1;TEST @Value(RELIABILITY) = 2;TEST @Value(RELIABILITY) = 3'L'BOOL_OP;OR;COMPOSITE_TEST;<Unused>;TEST @Value(RELIABILITY) = 4;TEST @Value(RELIABILITY) = 5;TEST @Value(RELIABILITY) = 6'M'BOOL_OP;OR;COMPOSITE_TEST;<Unused>;TEST @Value(RELIABILITY) = 7;TEST @Value(RELIABILITY) = 8;TEST @Value(RELIABILITY) = 9;TEST @Value(RELIABILITY) = 10'H'FME_NUM_CONDITIONS4___
      SET_TO LATITUDE = @Value(LAT)
      SET_TO LONGITUDE = @Value(LONG)
    -> AttributeFilter_8
AttributeFilter_8
    ATTR_VALUES = <EMPTY>,<MISSING>,<NULL>,<UNFILTERED>,HAZARD_ON_ROAD,HAZARD_ON_SHOULDER,HAZARD_WEATHER,HAZARD_ON_ROAD_OBJECT,HAZARD_ON_ROAD_POT_HOLE,HAZARD_ON_ROAD_ROAD_KILL,HAZARD_ON_SHOULDER_CAR_STOPPED,HAZARD_ON_SHOULDER_MISSING_SIGN,HAZARD_ON_SHOULDER_ANIMALS,HAZARD_WEATHER_FOG,HAZARD_WEATHER_HAIL,HAZARD_WEATHER_HEAVY_RAIN,HAZARD_WEATHER_HEAVY_SNOW,HAZARD_WEATHER_FLOOD,HAZARD_WEATHER_MONSOON,HAZARD_WEATHER_TORNADO,HAZARD_WEATHER_HEAT_WAVE,HAZARD_WEATHER_HURRICANE,HAZARD_WEATHER_FREEZING_RAIN,HAZARD_ON_ROAD_LANE_CLOSED,HAZARD_ON_ROAD_OIL,HAZARD_ON_ROAD_ICE,HAZARD_ON_ROAD_CONSTRUCTION,HAZARD_ON_ROAD_CAR_STOPPED,ROAD_CLOSED_HAZARD,ROAD_CLOSED_CONSTRUCTION,ROAD_CLOSED_EVENT,JAM_LIGHT_TRAFFIC,JAM_STAND_STILL_TRAFFIC,JAM_HEAVY_TRAFFIC,JAM_MODERATE_TRAFFIC,ACCIDENT_MAJOR,ACCIDENT_MINOR,POLICE_HIDING,POLICE_VISIBLE
    ATTR_NAME = SUBTYPE
    <UNFILTERED> -> AttributeFilter_9
    HAZARD_ON_ROAD -> warning_2
    HAZARD_ON_SHOULDER -> warning_2
    HAZARD_WEATHER -> weather_hazard_2
    HAZARD_ON_ROAD_OBJECT -> info_2
    HAZARD_ON_ROAD_POT_HOLE -> info_2
    HAZARD_ON_ROAD_ROAD_KILL -> warning_2
    HAZARD_ON_SHOULDER_CAR_STOPPED -> warning_2
    HAZARD_ON_SHOULDER_MISSING_SIGN -> info_2
    HAZARD_ON_SHOULDER_ANIMALS -> warning_2
    HAZARD_WEATHER_FOG -> weather_hazard_2
    HAZARD_WEATHER_HAIL -> weather_hazard_2
    HAZARD_WEATHER_HEAVY_RAIN -> weather_hazard_2
    HAZARD_WEATHER_HEAVY_SNOW -> weather_hazard_2
    HAZARD_WEATHER_FLOOD -> weather_hazard_2
    HAZARD_WEATHER_MONSOON -> weather_hazard_2
    HAZARD_WEATHER_TORNADO -> weather_hazard_2
    HAZARD_WEATHER_HEAT_WAVE -> weather_hazard_2
    HAZARD_WEATHER_HURRICANE -> weather_hazard_2
    HAZARD_WEATHER_FREEZING_RAIN -> weather_hazard_2
    HAZARD_ON_ROAD_LANE_CLOSED -> lane_closure_2
    HAZARD_ON_ROAD_OIL -> warning_2
    HAZARD_ON_ROAD_ICE -> weather_hazard_2
    HAZARD_ON_ROAD_CONSTRUCTION -> construction_2
    HAZARD_ON_ROAD_CAR_STOPPED -> warning_2
    ROAD_CLOSED_HAZARD -> closure_2
    ROAD_CLOSED_CONSTRUCTION -> closure_2
    ROAD_CLOSED_EVENT -> closure_2
    JAM_LIGHT_TRAFFIC -> info_2
    JAM_STAND_STILL_TRAFFIC -> heavy_standstill_traffic_2
    JAM_HEAVY_TRAFFIC -> heavy_standstill_traffic_2
    JAM_MODERATE_TRAFFIC -> moderate_traffic_2
    ACCIDENT_MAJOR -> accident_2
    ACCIDENT_MINOR -> accident_2
    POLICE_VISIBLE -> info_2
AttributeFilter_9
    ATTR_VALUES = <EMPTY>,<MISSING>,<NULL>,<UNFILTERED>,ACCIDENT,ROAD_CLOSED,CONSTRUCTION,MISC
    ATTR_NAME = TYPE
    <UNFILTERED> -> warning_2
    ACCIDENT -> accident_2
    ROAD_CLOSED -> closure_2
    CONSTRUCTION -> construction_2
    MISC -> info_2
warning_2: AttributeCreator
    ATTR_TABLE = SET_TO ICON = warning
    -> Historic (writer FILEGDB_2)
info_2: AttributeCreator
    ATTR_TABLE = SET_TO ICON = info
    -> Historic (writer FILEGDB_2)
construction_2: AttributeCreator
    ATTR_TABLE = SET_TO ICON = construction
    -> Historic (writer FILEGDB_2)
closure_2: AttributeCreator
    ATTR_TABLE = SET_TO ICON = closure
    -> Historic (writer FILEGDB_2)
accident_2: AttributeCreator
    ATTR_TABLE = SET_TO ICON = accident
    -> Historic (writer FILEGDB_2)
weather_hazard_2: AttributeCreator
    ATTR_TABLE = SET_TO ICON = weather_hazard
    -> Historic (writer FILEGDB_2)
lane_closure_2: AttributeCreator
    ATTR_TABLE = SET_TO ICON = lane_closure
    -> Historic (writer FILEGDB_2)
heavy_standstill_traffic_2: AttributeCreator
    ATTR_TABLE = SET_TO ICON = heavy_standstill_traffic
    -> Historic (writer FILEGDB_2)
moderate_traffic_2: AttributeCreator
    ATTR_TABLE = SET_TO ICON = moderate_traffic
    -> Historic (writer FILEGDB_2)
Historic (writer FILEGDB_2)
    attributes: ICON text(30), ICON_RELIABILITY text(7), LATITUDE text(25), LONGITUDE text(25), STREET text(40), LONG text(200), LAT text(200), BLOCKINGALERTUUID text(37), CITY text(19), COUNTRY text(3), DELAY double, DESCRIPTION text(61), ENDNODE text(19), IMAGEURL text(74), LENGTH double, LEVEL double, MAGVAR double, RELIABILITY double, REPORTRATING double, ROADTYPE double, SPEED double, STARTNODE text(12), SUBTYPE text(31), TURNTYPE text(5), TYPE text(14), UUID text(37), XYLINE text(895), XYPOINT text(38), pubDate text(31), DATETIME date,
      XYPOINT__ text(200), _match_id text(200), OBJECTID objectid, XYPOINT__00 text(200)

Bookmark: Geometry Creation
VertexCreator
    YVAL = @Value(LAT)
    INDEX = 0
    XVAL = @Value(LONG)
    MODE_NAME = Add Point
    -> Reprojector
Reprojector
    INTERPOLATION_TYPE_NAME = Nearest Neighbor
    RASTER_CELL_SIZE = Preserve Cells
    DEST = Iowa_LRS_Lambert
    SOURCE = EPSG:4326
    REPROJECTED -> NE

Bookmark: Surrounding States
NE: StringSearcher
    MATCHED_PARTS_ATTR = _matched_parts
    STRING_TO_SEARCH = @Value(CITY)
    CASE = no
    REGEXP = , NE
    MATCHED_RESULT_ATTR = _matched_characters
    MATCHED -> StreetType
    NOT_MATCHED -> MN
MN: StringSearcher
    MATCHED_PARTS_ATTR = _matched_parts
    STRING_TO_SEARCH = @Value(CITY)
    CASE = no
    REGEXP = , MN
    MATCHED_RESULT_ATTR = _matched_characters
    MATCHED -> StreetType
    NOT_MATCHED -> MO
MO: StringSearcher
    MATCHED_PARTS_ATTR = _matched_parts
    STRING_TO_SEARCH = @Value(CITY)
    CASE = no
    REGEXP = , MO
    MATCHED_RESULT_ATTR = _matched_characters
    MATCHED -> StreetType
    NOT_MATCHED -> SD
SD: StringSearcher
    MATCHED_PARTS_ATTR = _matched_parts
    STRING_TO_SEARCH = @Value(CITY)
    CASE = no
    REGEXP = , SD
    MATCHED_RESULT_ATTR = _matched_characters
    MATCHED -> StreetType
    NOT_MATCHED -> WI
WI: StringSearcher
    MATCHED_PARTS_ATTR = _matched_parts
    STRING_TO_SEARCH = @Value(CITY)
    CASE = no
    REGEXP = , WI
    MATCHED_RESULT_ATTR = _matched_characters
    MATCHED -> StreetType
    NOT_MATCHED -> IL
IL: StringSearcher
    MATCHED_PARTS_ATTR = _matched_parts
    STRING_TO_SEARCH = @Value(CITY)
    CASE = no
    REGEXP = , IL
    MATCHED_RESULT_ATTR = _matched_characters
    MATCHED -> StreetType
    NOT_MATCHED -> STREET_US-
StreetType: AttributeCreator
    ATTR_TABLE = SET_TO STREET_TYPE = SURR_
    -> AttributeCreator

Bookmark: Filter out Construction on Iowa State Roads
STREET_US-: StringSearcher
    MATCHED_PARTS_ATTR = _matched_parts
    STRING_TO_SEARCH = @Value(STREET)
    CASE = no
    REGEXP = US-
    MATCHED_RESULT_ATTR = _matched_characters
    MATCHED -> DESC_Construction
    NOT_MATCHED -> STREET_IA-
STREET_IA-: StringSearcher
    MATCHED_PARTS_ATTR = _matched_parts
    STRING_TO_SEARCH = @Value(STREET)
    CASE = no
    REGEXP = IA-
    MATCHED_RESULT_ATTR = _matched_characters
    MATCHED -> DESC_Construction
    NOT_MATCHED -> STREET_I-
STREET_I-: StringSearcher
    MATCHED_PARTS_ATTR = _matched_parts
    STRING_TO_SEARCH = @Value(STREET)
    CASE = no
    REGEXP = I-
    MATCHED_RESULT_ATTR = _matched_characters
    MATCHED -> DESC_Construction
    NOT_MATCHED -> CITY_US-
CITY_US-: StringSearcher
    MATCHED_PARTS_ATTR = _matched_parts
    STRING_TO_SEARCH = @Value(CITY)
    CASE = no
    REGEXP = US-
    MATCHED_RESULT_ATTR = _matched_characters
    MATCHED -> DESC_Construction
    NOT_MATCHED -> CITY_IA-
CITY_IA-: StringSearcher
    MATCHED_PARTS_ATTR = _matched_parts
    STRING_TO_SEARCH = @Value(CITY)
    CASE = no
    REGEXP = IA-
    MATCHED_RESULT_ATTR = _matched_characters
    MATCHED -> DESC_Construction
    NOT_MATCHED -> CITY_I-
CITY_I-: StringSearcher
    MATCHED_PARTS_ATTR = _matched_parts
    STRING_TO_SEARCH = @Value(CITY)
    CASE = no
    REGEXP = I-
    MATCHED_RESULT_ATTR = _matched_characters
    MATCHED -> DESC_Construction
    NOT_MATCHED -> LRS
DESC_Construction: StringSearcher
    MATCHED_PARTS_ATTR = _matched_parts
    STRING_TO_SEARCH = @Value(DESCRIPTION)
    CASE = no
    REGEXP = Construction
    MATCHED_RESULT_ATTR = _matched_characters
    NOT_MATCHED -> TYPE_Construction
TYPE_Construction: StringSearcher
    MATCHED_PARTS_ATTR = _matched_parts
    STRING_TO_SEARCH = @Value(TYPE)
    CASE = no
    REGEXP = Construction
    MATCHED_RESULT_ATTR = _matched_characters
    NOT_MATCHED -> SUBTYPE_Construction
SUBTYPE_Construction: StringSearcher
    MATCHED_PARTS_ATTR = _matched_parts
    STRING_TO_SEARCH = @Value(SUBTYPE)
    CASE = no
    REGEXP = Construction
    MATCHED_RESULT_ATTR = _matched_characters
    NOT_MATCHED -> LRS

Bookmark: LRS Process
  Note that you can replace this with your LRS.
LRS: AttributeManager
    ATTR_TABLE:
      REMOVE _matched_characters
      REMOVE _matched_parts{}.part
      REMOVE _matched_parts{}.startIndex
    -> DESC_Construction2
    -> AttributeCreator

Bookmark: Filter Out Construction (again)
DESC_Construction2: StringSearcher
    MATCHED_PARTS_ATTR = _matched_parts
    STRING_TO_SEARCH = @Value(DESCRIPTION)
    CASE = no
    REGEXP = Construction
    MATCHED_RESULT_ATTR = _matched_characters
    NOT_MATCHED -> TYPE_Construction2
TYPE_Construction2: StringSearcher
    MATCHED_PARTS_ATTR = _matched_parts
    STRING_TO_SEARCH = @Value(TYPE)
    CASE = no
    REGEXP = Construction
    MATCHED_RESULT_ATTR = _matched_characters
    NOT_MATCHED -> SUBTYPE_Construction2
SUBTYPE_Construction2: StringSearcher
    MATCHED_PARTS_ATTR = _matched_parts
    STRING_TO_SEARCH = @Value(SUBTYPE)
    CASE = no
    REGEXP = Construction
    MATCHED_RESULT_ATTR = _matched_characters
    NOT_MATCHED -> Matcher_5
    NOT_MATCHED -> Matcher_4

Bookmark: Existing Events Checker for Oracle Archives
Historic (reader FILEGDB_1)
    attributes: ICON text(30), ICON_RELIABILITY text(7), LATITUDE text(25), LONGITUDE text(25), STREET text(40), LONG text(200), LAT text(200), BLOCKINGALERTUUID text(37), CITY text(19), COUNTRY text(3), DELAY double, DESCRIPTION text(61), ENDNODE text(19), IMAGEURL text(74), LENGTH double, LEVEL double, MAGVAR double, RELIABILITY double, REPORTRATING double, ROADTYPE double, SPEED double, STARTNODE text(12), SUBTYPE text(31), TURNTYPE text(5), TYPE text(14), UUID text(37), XYLINE text(895), XYPOINT text(38), pubDate text(31), DATETIME date,
      XYPOINT__ text(200), _match_id text(200), OBJECTID objectid
    -> Matcher_4
Note: Filter out old events that are no longer coming through
Matcher_4
    MATCH_STRATEGY = Match Selected Attributes
    MATCH = NONE
    MATCHATTRS = UUID RELIABILITY
    LENIENT_MATCH = No
    CNT_ATTR = _match_id
    BLANK_AND_MISSING_DIFFER = Yes
    MATCHED -> Matcher_5
Note: Filter out events that have already been seen
Matcher_5
    MATCH_STRATEGY = Match Selected Attributes
    MATCH = NONE
    MATCHATTRS = UUID RELIABILITY
    LENIENT_MATCH = No
    CNT_ATTR = _match_id
    BLANK_AND_MISSING_DIFFER = Yes
    NOT_MATCHED -> TimeStamper_2
