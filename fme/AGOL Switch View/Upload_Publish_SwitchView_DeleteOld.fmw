FME workspace Upload_Publish_SwitchView_DeleteOld.fmw
Title: AGOL Update View Snippet
Description: This transformer was developed to provide an easier method to update large feature views hosted on ArcGIS Online.
1) Uploads a specified file geodatabase
2) Publishes the file geodatabase item as a service
3) Deletes the file geodatabase item
4) Updates the specified view to point to the newly published service
5) Deletes the old service
History: 20210702,DR,Version 1

Parameters:
- FGDBZipLocation = C:\FME\AllRoutes.zip   # FGDB File to Upload
- AGOL_User_Folder_ID = /
- AGOL_Connection = IowaDOT_GIS@AGOL   # "Esri ArcGIS Online"% ArcGIS Online Connection
- AGOL_Username = Username   # AGOL Username
- AGOL_Password =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   # AGOL Password
- ServiceBaseURL = https://services.arcgis.com/8lRhdTsQyJpO52F1   # Service Base URL
- View_Name = All_Routes_View   # Name of the View Service on ArcGIS Online
- View_Layer0_Name = All Routes   # View Layer 0 Name
- ItemName = AllRoutes   # Base Name for AGOL Items

Writers:
- FFS_1: FFS to C:\FME\$(ItemName).ffs

Note: Check Private Parameters when troubleshooting!
FeatureWriter
    DATASET = C:\FME\AllRoutes.zip\AllRoutes.gdb
    DATASET_ATTR = _dataset
    FEATURE_TYPE_LIST_ATTR = _feature_type
    FORMAT = GEODATABASE_FILE
    GEODATABASE_FILE_ANNOTATION_UNITS = unknown_units
    GEODATABASE_FILE_COMPRESS_AT_END = no
    GEODATABASE_FILE_COORDINATE_SYSTEM_GRANULARITY = FEATURE_TYPE
    GEODATABASE_FILE_DEFAULT_Z_VALUE = 0
    GEODATABASE_FILE_DESTINATION_DATASETTYPE_VALIDATION = Yes
    GEODATABASE_FILE_DUMP_FAILED_FEATURES = no
    GEODATABASE_FILE_ENABLE_FAST_DELETES = yes
    GEODATABASE_FILE_GRID_1 = 0
    GEODATABASE_FILE_HAS_MEASURES = no
    GEODATABASE_FILE_HAS_Z_VALUES = auto_detect
    GEODATABASE_FILE_IGNORE_FAILED_FEATURE_ENTRY = no
    GEODATABASE_FILE_MAX_NUMBER_FAILED_FEATURES = -1
    GEODATABASE_FILE_OVERWRITE_GEODB = NO
    GEODATABASE_FILE_REQUESTED_GEODATABASE_VERSION = CURRENT
    GEODATABASE_FILE_SIMPLIFY_GEOM = No
    GEODATABASE_FILE_SIMPLIFY_NETWORK_FEATURES = no
    GEODATABASE_FILE_TRANSACTION = 0
    GEODATABASE_FILE_TRANSACTION_INTERVAL = 5000
    GEODATABASE_FILE_TRANSACTION_TYPE = NONE
    GEODATABASE_FILE_VALIDATE_FEATURES = no
    GEODATABASE_FILE_XY_SCALE = 0
    GEODATABASE_FILE_X_ORIGIN = 0
    GEODATABASE_FILE_Y_ORIGIN = 0
    GEODATABASE_FILE_Z_ORIGIN = 0
    GEODATABASE_FILE_Z_SCALE = 0
    TOTAL_FEATURES_WRITTEN_ATTR = _total_features_written
    SUMMARY -> AttributeManager_6

Bookmark: AGOL
AttributeManager_6
    ATTR_TABLE:
      SET_TO BaseName = $(ItemName)
      SET_TO BaseName.FGDB = $(ItemName)FGDB@Left(@DateTimeNow(),12)
      SET_TO BaseName.Service = $(ItemName)FS@Left(@DateTimeNow(),12)
    -> UploadFGDBtoAGOL
UploadFGDBtoAGOL: ArcGISOnlineConnector
    OPERATION_TYPE = Upload
    PARAMETER_SETUP = _FME_SOURCE_TYPE]File]_FME_SOURCE_FILE]$(FGDBZipLocation)]_FME_DATA_TO_UPLOAD]<Unused>]_UPLOAD_FILE_TITLE]@Value(BaseName.FGDB)]FILE_ITEM_TYPE]File Geodatabase]_UPLOAD_FILE_TAGS]FMEFGDB]_FME_UPLOAD_DESTINATION_PATH]$(AGOL_User_Folder_ID)]_FME_UPLOAD_ATTR_FILENAME]<Unused>]_UPLOAD_FME_ATTRIBUTES_TO_ADD]"_id _private_url"]FME_CONTROLLER_QUERY_FILE]esri_agol_deps/Upload.fme
    __arcgisonlineconnector_connection = $(AGOL_Connection)
    -> AttributeManager_3
    <REJECTED> -> Terminator
AttributeManager_3
    ATTR_TABLE:
      REMOVE _feature_type{}.count
      REMOVE _feature_type{}.name
      REMOVE _dataset
      REMOVE _total_features_written
      RENAME_SET_VALUE _id > id.FGDB
      REMOVE _private_url
    -> PublishNewServicetoAGOL
PublishNewServicetoAGOL: ArcGISOnlineConnector
    OPERATION_TYPE = Publish
    PARAMETER_SETUP = _FME_FILEID]@Value(id.FGDB)]_PUBLISH_FILE_TITLE]@Value(BaseName.Service)]_PUBLISH_FILE_TAGS]FMEService]FILE_COORD_SYSTEM]SPHERICAL_MERCATOR]WAIT_BEHAVIOUR]Yes]WAIT_TIMEOUT]600]_PUBLISH_FME_ATTRIBUTES_TO_ADD]"_id _private_url"]FME_CONTROLLER_QUERY_FILE]esri_agol_deps/Publish.fme
    __arcgisonlineconnector_connection = $(AGOL_Connection)
    -> AttributeManager_4
    <REJECTED> -> Terminator_2
AttributeManager_4
    ATTR_TABLE:
      RENAME_SET_VALUE _id > id.NewService
      REMOVE _private_url
    -> DeleteFGDB
Note: Disable this connection when running for the first time
Note: Enable this connection when running for the first time to populate the ffs
DeleteFGDB: ArcGISOnlineConnector
    OPERATION_TYPE = Delete
    PARAMETER_SETUP = _FME_FILEID]@Value(id.FGDB)]FME_CONTROLLER_QUERY_FILE]esri_agol_deps/Delete.fme
    __arcgisonlineconnector_connection = $(AGOL_Connection)
    -> CreateToken
    -> AttributeManager_2 [off]
ReadFFSwithCurrentServiceID: FeatureReader
    ATTRIBUTES = AllRoutes,"id.OldService,_creation_instance"
    ATTR_ACCUM_MODE = Merge Initiator and Result
    ATTR_CONFLICT_RES = Use Result
    COMBINE_GEOM = Use Result
    DATASET = C:\FME\$(ItemName).ffs
    FEATURETYPES = $(ItemName)
    FFS_USE_SEARCH_ENVELOPE = NO
    FORMAT = FFS
    INTERACT = <No Spatial Filter>
    OUTPUT_FEATURES_DISPLAY = Schema and Data Features
    AllRoutes -> DeleteOldService
DeleteOldService: ArcGISOnlineConnector
    OPERATION_TYPE = Delete
    PARAMETER_SETUP = _FME_FILEID]@Value(id.OldService)]FME_CONTROLLER_QUERY_FILE]esri_agol_deps/Delete.fme
    __arcgisonlineconnector_connection = $(AGOL_Connection)
    -> AttributeManager_2
AttributeManager_2
    ATTR_TABLE:
      REMOVE id.FGDB
      REMOVE BaseName
      REMOVE BaseName.FGDB
      REMOVE BaseName.Service
      REMOVE _response_body
      REMOVE _http_status_code
      REMOVE token
      REMOVE id.OldService
      RENAME_SET_VALUE id.NewService > id.OldService
    -> AllRoutes (writer FFS_1)
AllRoutes (writer FFS_1)
    attributes: id.OldService varchar(200), _creation_instance uint64
Terminator_2
    MESSAGE = AGOL ERROR: Failed publishing the new service
Terminator
    MESSAGE = AGOL ERROR: There is already an existing item with the same item name OR same file name on ArcGIS Online. Rename your file and try again.

Bookmark: Switch the view from the old service to the new service
CreateToken: HTTPCaller
    CONNECTION_TIMEOUT_LENGTH = 60
    ERROR_ATTR = _error
    FOLLOW_REDIRECTS = FOLLOW_WITH_GET
    HTTP_METHOD = POST
    MULTIPARTS = username StringUpload SOURCE_EXPRESSION;$(AGOL_Username);MIME_TYPE;text/plain;FME_CONTROLLER_QUERY_FILE;transformers/dependencies/http/StringUpload.fme password StringUpload SOURCE_EXPRESSION;$(AGOL_Password);MIME_TYPE;text/plain;FME_CONTROLLER_QUERY_FILE;transformers/dependencies/http/StringUpload.fme referer StringUpload SOURCE_EXPRESSION;https://www.arcgis.com;MIME_TYPE;text/plain;FME_CONTROLLER_QUERY_FILE;transformers/dependencies/http/StringUpload.fme f StringUpload SOURCE_EXPRESSION;json;MIME_TYPE;text/plain;FME_CONTROLLER_QUERY_FILE;transformers/dependencies/http/StringUpload.fme
    REDIRECT_AUTH = ORIGINAL_DOMAIN_ONLY
    SAVE_FILE = Attribute
    STATUS_CODE_ATTR = _http_status_code
    TARGET_ATTR = _response_body
    TARGET_ATTR_ENCODING = auto-detect
    TARGET_URL = https://arcgis.com/sharing/rest/generateToken
    TRANSFER_TIMEOUT_LENGTH = 90
    UPLOAD_TYPE = Multipart / Form Data
    USE_COOKIES = No
    VERIFY_SSL_CERTIFICATES = Yes
    -> JSONFlattener
JSONFlattener
    ERROR_LIST_ATTR = _json_error
    JSON_DOCUMENT = @Value(_response_body)
    NEW_ATTRIBUTES = token
    READ_FROM_FILE = NO
    RECURSIVE = Yes
    -> DeleteLayers
DeleteLayers: HTTPCaller
    CONNECTION_TIMEOUT_LENGTH = 60
    ERROR_ATTR = _error
    FOLLOW_REDIRECTS = FOLLOW_WITH_GET
    HTTP_METHOD = POST
    MULTIPARTS = deleteFromDefinition StringUpload SOURCE_EXPRESSION;{"layers":[{"id": 0}]};MIME_TYPE;text/plain;FME_CONTROLLER_QUERY_FILE;transformers/dependencies/http/StringUpload.fme async StringUpload SOURCE_EXPRESSION;false;MIME_TYPE;text/plain;FME_CONTROLLER_QUERY_FILE;transformers/dependencies/http/StringUpload.fme f StringUpload SOURCE_EXPRESSION;json;MIME_TYPE;text/plain;FME_CONTROLLER_QUERY_FILE;transformers/dependencies/http/StringUpload.fme
    REDIRECT_AUTH = ORIGINAL_DOMAIN_ONLY
    SAVE_FILE = Attribute
    STATUS_CODE_ATTR = _http_status_code
    TARGET_ATTR = _response_body
    TARGET_ATTR_ENCODING = auto-detect
    TARGET_URL = $(ServiceBaseURL)/arcgis/rest/admin/services/$(View_Name)/FeatureServer/deleteFromDefinition?f=pjson&token=@Value(token)
    TRANSFER_TIMEOUT_LENGTH = 90
    UPLOAD_TYPE = Multipart / Form Data
    USE_COOKIES = No
    VERIFY_SSL_CERTIFICATES = Yes
    -> DeleteLayersResponse
DeleteLayersResponse: Logger
    LOG_FEATURE = LOG_ONLY
    MAXCOORDS = 20
    MAXFEATS = 20
    MESSAGE:
      Response from Delete Request ($(ServiceBaseURL)/arcgis/rest/admin/services/$(View_Name)/FeatureServer/deleteFromDefinition?f=pjson&token=@Value(token))
      @Value(_response_body)
    SEVERITY = INFO
    LOGGED -> AddLayers
AddLayers: HTTPCaller
    CONNECTION_TIMEOUT_LENGTH = 60
    ERROR_ATTR = _error
    FOLLOW_REDIRECTS = FOLLOW_WITH_GET
    HTTP_METHOD = POST
    MULTIPARTS = addToDefinition StringUpload SOURCE_EXPRESSION;{"layers":[{"adminLayerInfo":{"geometryField":{"name":"Shape"},"xssTrustedFields":"","viewLayerDefinition":{"sourceServiceName":"@Value(BaseName.Service)","sourceLayerId":0,"sourceLayerFields":"*"}},"id":0,"name":"$(View_Layer0_Name)"}]};MIME_TYPE;text/plain;FME_CONTROLLER_QUERY_FILE;transformers/dependencies/http/StringUpload.fme async StringUpload SOURCE_EXPRESSION;false;MIME_TYPE;text/plain;FME_CONTROLLER_QUERY_FILE;transformers/dependencies/http/StringUpload.fme f StringUpload SOURCE_EXPRESSION;json;MIME_TYPE;text/plain;FME_CONTROLLER_QUERY_FILE;transformers/dependencies/http/StringUpload.fme
    REDIRECT_AUTH = ORIGINAL_DOMAIN_ONLY
    SAVE_FILE = Attribute
    STATUS_CODE_ATTR = _http_status_code
    TARGET_ATTR = _response_body
    TARGET_ATTR_ENCODING = auto-detect
    TARGET_URL = $(ServiceBaseURL)/arcgis/rest/admin/services/$(View_Name)/FeatureServer/addToDefinition?f=pjson&token=@Value(token)
    TRANSFER_TIMEOUT_LENGTH = 90
    UPLOAD_TYPE = Multipart / Form Data
    USE_COOKIES = No
    VERIFY_SSL_CERTIFICATES = Yes
    -> AddLayersResponse
AddLayersResponse: Logger
    LOG_FEATURE = LOG_ONLY
    MAXCOORDS = 20
    MAXFEATS = 20
    MESSAGE:
      Response from Add Request ($(ServiceBaseURL)/arcgis/rest/admin/services/$(View_Name)/FeatureServer/addToDefinition?f=pjson&token=@Value(token))
      @Value(_response_body)
    SEVERITY = INFO
    LOGGED -> ReadFFSwithCurrentServiceID [INITIATOR]
